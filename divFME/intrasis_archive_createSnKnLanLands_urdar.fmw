FME workspace intrasis_archive_createSnKnLanLands_urdar.fmw

Parameters:
- DestDataset_OGCGEOPACKAGE = C:\Users\krima354\Work Folders\Documents\kicki_arbetsfiler\slask\site_info3.gpkg   # GeoPackage File
- SourceDataset_OGCGEOPACKAGE_5 = C:\Users\krima354\Work Folders\Documents\kicki_arbetsfiler\urdar_arbetsfiler\create_siteinfo\intrasis_archive.gpkg   # GeoPackage File
- SourceDataset_OGCGEOPACKAGE = C:\Users\krima354\Work Folders\Documents\kicki_arbetsfiler\GETdata\arkeologiska_uppdrag_undersökningsområden_sverige.gpkg   # GeoPackage File
- SourceDataset_SHAPEFILE_5 = C:\Users\krima354\Work Folders\Documents\kicki_arbetsfiler\GETdata\shape_svenska_220223\KommunSweref99TM\Kommun_Sweref99TM_region.shp   # Source Esri Shapefile(s)
- SourceDataset_SHAPEFILE_4 = C:\Users\krima354\Work Folders\Documents\kicki_arbetsfiler\GETdata\shape_svenska_220223\LanSweref99TM\Lan_Sweref99TM_region.shp   # Source Esri Shapefile(s)
- SourceDataset_SHAPEFILE = C:\Users\krima354\Work Folders\Documents\kicki_arbetsfiler\GETdata\Kopia av landskap_shp\landskap\svelandskap_2010_rev_granser.shp   # Source Esri Shapefile(s)
- SourceDataset_OGCGEOPACKAGE_2 = C:\Users\krima354\Work Folders\Documents\kicki_arbetsfiler\GETdata\sockenstad.gpkg   # GeoPackage File

Readers:
- SHAPEFILE_1: SHAPEFILE from $(SourceDataset_SHAPEFILE) in EPSG:3006
- SHAPEFILE_2: SHAPEFILE from $(SourceDataset_SHAPEFILE_5) in EPSG:3006
- SHAPEFILE_3: SHAPEFILE from $(SourceDataset_SHAPEFILE_4) in EPSG:3006
- OGCGEOPACKAGE_3: OGCGEOPACKAGE from $(SourceDataset_OGCGEOPACKAGE_2) in EPSG:3006
- OGCGEOPACKAGE_1: OGCGEOPACKAGE from $(SourceDataset_OGCGEOPACKAGE) in EPSG:3006
- OGCGEOPACKAGE_4: OGCGEOPACKAGE from $(SourceDataset_OGCGEOPACKAGE_5) in EPSG:3006

Writers:
- OGCGEOPACKAGE_2: OGCGEOPACKAGE to $(DestDataset_OGCGEOPACKAGE) in EPSG:3006

arkeologiska_uppdrag_undersökningsområden_sverige_polygon (reader OGCGEOPACKAGE_1)
    attributes: id text(255), uppdragsnummer text(9), beslutande_myndighet text(255), beslutsdatum date, diarienummer text(255), uppdragstyp text(255), utforande_organisation text(255), nollresultat text(9), url text(255), status text(255), lan text, kommun text, socken text, fid int,PrimaryKey
    -> BoundingBoxAccumulator_2
arkeologiska_uppdrag_undersökningsområden_sverige_linestring (reader OGCGEOPACKAGE_1)
    attributes: id text(255), uppdragsnummer text(9), beslutande_myndighet text(255), beslutsdatum date, diarienummer text(255), uppdragstyp text(255), utforande_organisation text(255), nollresultat text(9), url text(255), status text(255), lan text, kommun text, socken text, fid int,PrimaryKey
    -> Bufferer
Bufferer
    ANGLE = 22.5
    CAP_STYLE = Arc
    CORNER_STYLE = Arc
    MODE = AREA
    OFFSET = 500
    OFFSET_UNITS = METERS
    PRECISION = APPROX
    BUFFERED -> SpatialFilter_5 [Filter]
arkeologiska_uppdrag_undersökningsområden_sverige_point (reader OGCGEOPACKAGE_1)
    attributes: id text(255), uppdragsnummer text(9), beslutande_myndighet text(255), beslutsdatum date, diarienummer text(255), uppdragstyp text(255), utforande_organisation text(255), nollresultat text(9), url text(255), status text(255), lan text, kommun text, socken text, fid int,PrimaryKey
    -> Bufferer_2
Bufferer_2
    ANGLE = 22.5
    CAP_STYLE = Arc
    CORNER_STYLE = Arc
    MODE = AREA
    OFFSET = 500
    OFFSET_UNITS = METERS
    PRECISION = APPROX
    BUFFERED -> SpatialFilter_5 [Filter]
geom (reader OGCGEOPACKAGE_4)
    attributes: ObjectId mediumint, MetaId mediumint, SymbolId mediumint, the_raster text(200), intrasis_archive text(200), id int,PrimaryKey
    -> SpatialFilter_2 [Candidate]
point (reader OGCGEOPACKAGE_4)
    attributes: ObjectId mediumint, MetaId mediumint, SymbolId mediumint, the_raster text(200), _inside_x double, _inside_y double, _inside_z double, intrasis_archive text(200), id int,PrimaryKey
    -> SpatialFilter_2 [Candidate]
boundingbox (reader OGCGEOPACKAGE_4)
    attributes: ObjectId mediumint, MetaId mediumint, SymbolId mediumint, the_raster text(200), intrasis_archive text(200), id int,PrimaryKey
    -> SpatialFilter_2 [Candidate]
sockenstad (reader OGCGEOPACKAGE_3)
    attributes: objektidentitet text(36), objektversion smallint, version_giltig_fran text(16), sockenstadkod text(4), sockenstadnamn text(100), sockenstadtyp smallint, omradesnummer smallint, huvudomrade text(1), sockenstadanmarkning text(254), OBJECTID int,PrimaryKey
    -> SpatialFilter_2 [Filter]
Kommun_Sweref99TM_region (reader SHAPEFILE_2)
    attributes: KnKod varchar(4), KnNamn varchar(15)
    -> SpatialFilter [Filter]
Lan_Sweref99TM_region (reader SHAPEFILE_3)
    attributes: LnKod varchar(2), LnNamn varchar(20)
    -> SpatialFilter_4 [Filter]
svelandskap_2010_rev_granser (reader SHAPEFILE_1)
    attributes: LANDSKAP varchar(254), ID number(16,0), KOMMENTAR varchar(150), SKALA varchar(100), AREA_METER double, PERIMETER_ double, HECTARES double
    -> SpatialFilter_3 [Filter]
siteinfo (writer OGCGEOPACKAGE_2)
    attributes: intrasis_archive text(200), sockenstadnamn text(100), sockenstadtyp smallint, LanNamn text(20), KnNamn text(15), Landskap text(254), uppdragsnummer text(9), url_fran_upp text(255), status_fran_upp text(255), lan_fran_upp text, kommun_fran_upp text, socken_fran_upp text

Bookmark: uppdragsnunmmer
BoundingBoxAccumulator_2
    ACCUM_ATTRS_NAME = Use Attributes From One Feature
    GROUP_BY = uppdragsnummer
    BOUNDING_BOX -> SpatialFilter_5 [Filter]
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS CONTAINS TOUCHES
    USE_BOUNDING_BOX = No
    PASSED -> AttributeManager
    FAILED -> AttributeManager
AttributeManager
    ATTR_TABLE:
      REMOVE ObjectId
      REMOVE MetaId
      REMOVE SymbolId
      REMOVE the_raster
      REMOVE _predicate
      REMOVE objektidentitet
      REMOVE objektversion
      REMOVE version_giltig_fran
      REMOVE sockenstadkod
      REMOVE omradesnummer
      REMOVE huvudomrade
      REMOVE sockenstadanmarkning
      REMOVE OBJECTID
      REMOVE id
      REMOVE _inside_x
      REMOVE _inside_y
      REMOVE _inside_z
    -> SpatialFilter [Candidate]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS WITHIN CONTAINS
    USE_BOUNDING_BOX = No
    PASSED -> AttributeManager_3
    FAILED -> AttributeManager_3
AttributeManager_3
    ATTR_TABLE:
      REMOVE KnKod
      REMOVE _predicate
    -> SpatialFilter_4 [Candidate]
SpatialFilter_4
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS WITHIN CONTAINS
    USE_BOUNDING_BOX = No
    PASSED -> AttributeManager_4
    FAILED -> AttributeManager_4
AttributeManager_4
    ATTR_TABLE:
      REMOVE LnKod
      RENAME_SET_VALUE LnNamn > LanNamn
      REMOVE _predicate
    -> SpatialFilter_3 [Candidate]
SpatialFilter_3
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS WITHIN CONTAINS
    USE_BOUNDING_BOX = No
    PASSED -> AttributeManager_5
    FAILED -> AttributeManager_5
AttributeManager_5
    ATTR_TABLE:
      REMOVE ID
      REMOVE KOMMENTAR
      REMOVE SKALA
      REMOVE AREA_METER
      REMOVE PERIMETER_
      REMOVE HECTARES
      RENAME_SET_VALUE LANDSKAP > Landskap
      REMOVE _predicate
    -> SpatialFilter_5 [Candidate]
SpatialFilter_5
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = WITHIN CONTAINS INTERSECTS
    USE_BOUNDING_BOX = No
    PASSED -> AttributeManager_2
    FAILED -> AttributeManager_2
AttributeManager_2
    ATTR_TABLE:
      REMOVE id
      REMOVE beslutande_myndighet
      REMOVE beslutsdatum
      REMOVE diarienummer
      REMOVE uppdragstyp
      REMOVE utforande_organisation
      REMOVE nollresultat
      RENAME_SET_VALUE url > url_fran_upp
      RENAME_SET_VALUE status > status_fran_upp
      RENAME_SET_VALUE lan > lan_fran_upp
      RENAME_SET_VALUE kommun > kommun_fran_upp
      RENAME_SET_VALUE socken > socken_fran_upp
      REMOVE _predicate
    -> siteinfo (writer OGCGEOPACKAGE_2)
