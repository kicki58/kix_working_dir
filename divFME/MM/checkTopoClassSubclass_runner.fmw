FME workspace checkTopoClassSubclass_runner.fmw

Parameters:
- server = uuc-srv390   # Server
- postgres_db = postgres
- port = 5432   # Port
- user = postgres   # User
- psswd = Secret_1   # Password
- DestDataset_XLSXW = $(FME_MF_DIR)topo2.xlsx   # Destination Microsoft Excel File

Readers:
- POSTGRES_1: POSTGRES from $(postgres_db)

pg_database (reader POSTGRES_1)
    attributes: oid oid,Unique, datname text,Unique, datdba oid, encoding int4, datcollate text, datctype text, datistemplate bool, datallowconn bool, datconnlimit int4, datlastsysoid oid, datfrozenxid text, datminmxid text, dattablespace oid, datacl text
    -> WorkspaceRunner
WorkspaceRunner
    BLOCKING = Yes
    WORKSPACE_FILE = $(FME_MF_DIR)checkTopoClassSubclass.fmw
    WORKSPACE_PARAMETERS = SourceDataset_POSTGRES_2,@Value(datname),HOST_POSTGRES,$(server),PORT_POSTGRES,$(port),PASSWORD_POSTGRES,$(psswd),DestDataset_XLSXW,$(DestDataset_XLSXW),USER_NAME_POSTGRES,$(user)
