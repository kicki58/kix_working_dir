FME workspace 4_fix_attributes_on_object2.fmw

Parameters:
- SourcDestDataset_mm_gpkg = C:\ny_slask\mm_2\MK7634_TEST3.gpkg   # Dest SQLlite/gpkg
- SourceDataset_mall = C:\ny_slask\mm_2\mall2.gpkg   # Mall reader SQLite/gpkg

Readers:
- OGCGEOPACKAGE_1: OGCGEOPACKAGE from $(SourcDestDataset_mm_gpkg)
- SQLITE3_3: SQLITE3 from $(SourceDataset_mall)
- SQLITE3_1: SQLITE3 from $(SourcDestDataset_mm_gpkg)

attributes (reader OGCGEOPACKAGE_1)
    attributes: object_id int, attribute_label text, attribute_value text, attribute_unit text, class int, data_type text, attribute_id int
    -> AttributeManager
AttributeManager
    ATTR_TABLE = SET_TO new_attr (varchar(200)) = @Value(attribute_label): @Value(attribute_value) @Value(attribute_unit)
    -> ListBuilder
ListBuilder
    GROUP_BY = object_id
    LIST_ATTRS_TO_INCLUDE = new_attr
    LIST_NAME = _list
    -> ListConcatenator
ListConcatenator
    DROP_EMPTY_PARTS = No
    LIST_ATTR = _list{}.new_attr
    SEP = ,
    VAL_ATTR = attributes
    -> FeatureMerger [SUPPLIER]
objects (reader SQLITE3_1)
    attributes: IntrasisId integer, Name text, Class text, SubClass text, Color integer, geometry_count integer, attributes text, object_id integer
    -> AttributeRemover
AttributeRemover
    REMOVE_ATTRS = attributes,geometry_count
    -> FeatureMerger [REQUESTOR]
FeatureMerger
    ATTR_ACCUM_MODE = Merge Supplier
    ATTR_CONFLICT_RES_LOOKUP = REQUESTOR_IF_CONFLICT
    IGNORE_NULLS = No
    JOIN_KEYS = @Value(object_id) @Value(object_id) AUTO
    MERGE_TYPE = Attributes Only
    PROCESS_DUPS = NO
    REJECT_NULL_MISSING_KEYS = No
    SUPPLIERS_FIRST = No
    ATTR_CONFLICT_RES = Use Requestor
    MERGED -> FeatureMerger_2 [REQUESTOR]
features (reader OGCGEOPACKAGE_1)
    attributes: object_id int, SymbolId int, GeoObjectId int, spatial_type text, fid int, id int,PrimaryKey
    -> ListBuilder_2
ListBuilder_2
    GROUP_BY = object_id
    LIST_ATTRS_TO_INCLUDE = id object_id
    LIST_NAME = _list
    -> ListElementCounter
ListElementCounter
    CNT_ATTR = geometry_count
    LIST_NAME = _list{}
    -> FeatureMerger_2 [SUPPLIER]
FeatureMerger_2
    ATTR_ACCUM_MODE = Merge Supplier
    ATTR_CONFLICT_RES_LOOKUP = REQUESTOR_IF_CONFLICT
    IGNORE_NULLS = No
    JOIN_KEYS = @Value(object_id) @Value(object_id) AUTO
    MERGE_TYPE = Attributes Only
    PROCESS_DUPS = NO
    REJECT_NULL_MISSING_KEYS = No
    SUPPLIERS_FIRST = No
    ATTR_CONFLICT_RES = Use Requestor
    MERGED -> FeatureWriter [objects]
    UNMERGED_REQUESTOR -> AttributeManager_2
AttributeManager_2
    ATTR_TABLE = SET_TO geometry_count (uint8) = 0
    -> FeatureWriter [objects]
FeatureWriter
    DATASET = $(SourcDestDataset_mm_gpkg)
    DATASET_ATTR = _dataset
    FEATURE_TYPE_LIST_ATTR = _feature_types
    FORMAT = SQLITE3
    SQLITE3_COORDINATE_SYSTEM_GRANULARITY = FEATURE
    SQLITE3_DESTINATION_DATASETTYPE_VALIDATION = Yes
    SQLITE3_ENCODING = utf-8
    SQLITE3_OVERWRITE_FILE = No
    SQLITE3_SUPPORT_INTERNATIONALIZATION = YES
    SQLITE3_TRANSACTION_INTERVAL = 500
    SQLITE3_WRITER_MODE = INSERT
    TOTAL_FEATURES_WRITTEN_ATTR = _total_features_written

Bookmark: gpkg extensions
gpkg_extensions (reader SQLITE3_3)
    attributes: table_name text,Unique, column_name text,Unique, extension_name text,Unique, definition text, scope text
    -> Tester_2
Tester_2
    BOOL_OP = AND
    TEST_CLAUSE:
      TEST @Value(table_name) != features
      TEST @Value(table_name) != project_information
    TEST_MODE = TEST
    PASSED -> FeatureWriter [gpkg_extensions]
gpkgext_relations (reader SQLITE3_3)
    attributes: id integer, base_table_name text, base_primary_column text, related_table_name text, related_primary_column text, relation_name text, mapping_table_name text,Unique
    -> FeatureWriter [gpkgext_relations]

Bookmark: METADATA
gpkg_metadata (reader SQLITE3_3)
    attributes: id integer, md_scope text, md_standard_uri text, mime_type text, metadata text
    -> FeatureWriter [gpkg_metadata]
gpkg_metadata_reference (reader SQLITE3_3)
    attributes: reference_scope text, table_name text, column_name text, row_id_value integer, timestamp text, md_file_id integer, md_parent_id integer
    -> FeatureWriter [gpkg_metadata_reference]
