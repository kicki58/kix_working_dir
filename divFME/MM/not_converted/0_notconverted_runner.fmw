FME workspace 0_notconverted_runner.fmw

Parameters:
- DestDataset_SQLITE3 = C:\ny_slask\mm_2\MK7634_TEST.gpkg   # Dest SQLlite/gpkg
- db_namne = MK7634   # MSSQL db
- SourceDataset_mall = C:\ny_slask\mm_2\mall2.gpkg   # Mall reader SQLite/gpkg
- SourceDataset_SHAPEFILE = ""C:\Users\krima354\Downloads\Backup_FILER\Backup_FILER\IntrasisData\MK7634\geodata\Polygon.shp" "C:\Users\krima354\Downloads\Backup_FILER\Backup_FILER\IntrasisData\MK7634\geodata\LPolygon.shp" "C:\Users\krima354\Downloads\Backup_FILER\Backup_FILER\IntrasisData\MK7634\geodata\Line.shp" "C:\Users\krima354\Downloads\Backup_FILER\Backup_FILER\IntrasisData\MK7634\geodata\ILine.shp" "C:\Users\krima354\Downloads\Backup_FILER\Backup_FILER\IntrasisData\MK7634\geodata\IMultiP.shp" "C:\Users\krima354\Downloads\Backup_FILER\Backup_FILER\IntrasisData\MK7634\geodata\IPoint.shp" "C:\Users\krima354\Downloads\Backup_FILER\Backup_FILER\IntrasisData\MK7634\geodata\IPolygon.shp" "C:\Users\krima354\Downloads\Backup_FILER\Backup_FILER\IntrasisData\MK7634\geodata\LLine.shp" "C:\Users\krima354\Downloads\Backup_FILER\Backup_FILER\IntrasisData\MK7634\geodata\LMultiP.shp" "C:\Users\krima354\Downloads\Backup_FILER\Backup_FILER\IntrasisData\MK7634\geodata\LPoint.shp" "C:\Users\krima354\Downloads\Backup_FILER\Backup_FILER\IntrasisData\MK7634\geodata\MultiP.shp" "C:\Users\krima354\Downloads\Backup_FILER\Backup_FILER\IntrasisData\MK7634\geodata\Point.shp""   # Source Esri Shapefile(s)

Creator
    GEOMTYPE = Geometry Object
    NUM = 1
    CREATED -> WorkspaceRunner_6
Note: 1_write_features
WorkspaceRunner_6
    BLOCKING = Yes
    WORKSPACE_FILE = $(FME_MF_DIR_ENCODED)1_writeFeatures.fmw
    WORKSPACE_PARAMETERS = SourceDataset_SHAPEFILE,$(SourceDataset_SHAPEFILE),SourceDataset_MSSQL_ADO,$(db_namne),DestDataset_OGCGEOPACKAGE,$(DestDataset_SQLITE3)
    SUCCEEDED -> WorkspaceRunner
Note: 2_export_from_MSSQL2.fmw
WorkspaceRunner
    BLOCKING = Yes
    WORKSPACE_FILE = $(FME_MF_DIR_ENCODED)2_export_from_MSSQL2.fmw
    WORKSPACE_PARAMETERS = SourceDataset_SHAPEFILE,$(SourceDataset_SHAPEFILE),SourceDataset_MSSQL_ADO,$(db_namne),DestDataset_OGCGEOPACKAGE,$(DestDataset_SQLITE3)
    SUCCEEDED -> WorkspaceRunner_5
Note: 3_project_information.fmw
WorkspaceRunner_5
    BLOCKING = Yes
    WORKSPACE_FILE = $(FME_MF_DIR_ENCODED)3_project_information.fmw
    WORKSPACE_PARAMETERS = DestDataset_SQLITE3,$(DestDataset_SQLITE3)
    SUCCEEDED -> WorkspaceRunner_2
Note: 4_fix_attributes_on_object2.fmw
WorkspaceRunner_2
    BLOCKING = Yes
    WORKSPACE_FILE = $(FME_MF_DIR_ENCODED)4_fix_attributes_on_object2.fmw
    WORKSPACE_PARAMETERS = SourcDestDataset_mm_gpkg,$(DestDataset_SQLITE3),SourceDataset_mall,$(SourceDataset_mall)
    SUCCEEDED -> WorkspaceRunner_3
Note: 5_views.fmw
WorkspaceRunner_3
    BLOCKING = Yes
    WORKSPACE_FILE = $(FME_MF_DIR_ENCODED)5_views.fmw
    WORKSPACE_PARAMETERS = SourceDestDataset_MM,$(DestDataset_SQLITE3)
    SUCCEEDED -> WorkspaceRunner_4
Note: 6_fix_gpkg_tables2.fmw
WorkspaceRunner_4
    BLOCKING = Yes
    WORKSPACE_FILE = $(FME_MF_DIR_ENCODED)6_fix_gpkg_tables2.fmw
    WORKSPACE_PARAMETERS = SourceDestDataset_MM,$(DestDataset_SQLITE3),SourceDataset_SQLITE3,$(SourceDataset_mall)
