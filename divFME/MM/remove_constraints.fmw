FME workspace remove_constraints.fmw

SQLCreator
    DATASET = EPI-4L2CTD3
    EXPOSED_ATTRIBUTE_LIST = name
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = EPI-4L2CTD3
    MSSQL_ADO_QUERY_FEATURE_TYPES_FOR_MERGE_FILTERS = Yes
    OUTPUT_FEATURES_DISPLAY = Schema and Data Features
    SQL_STATEMENT = select name from master.sys.databases
    RESULT -> SQLExecutor [INITIATOR]
SQLExecutor
    COMBINE_ATTRS = Result Attributes Only
    COMBINE_GEOM = Initiator Geometry Only
    DATASET = sa@EPI-4L2CTD3
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = sa@EPI-4L2CTD3
    MSSQL_ADO_QUERY_FEATURE_TYPES_FOR_MERGE_FILTERS = Yes
    OUTPUT_FEATURES_DISPLAY = Schema and Data Features
    SQL_STATEMENT:
      FME_SQL_DELIMITER ;

      USE [@Value(name)];


      ALTER TABLE [dbo].[Attribute] DROP CONSTRAINT [FK_Atribute_AttributeDef];


      ALTER TABLE [dbo].[Attribute]  WITH CHECK ADD  CONSTRAINT [FK_Atribute_AttributeDef] FOREIGN KEY([MetaId])
      REFERENCES [dbo].[AttributeDef] ([MetaId])
      ON DELETE CASCADE;

      ALTER TABLE [dbo].[Attribute] CHECK CONSTRAINT [FK_Atribute_AttributeDef];

      ALTER TABLE [dbo].[AttributeValue] DROP CONSTRAINT [FK_AttributeValue_Atribute];

      ALTER TABLE [dbo].[AttributeValue]  WITH NOCHECK ADD  CONSTRAINT [FK_AttributeValue_Atribute] FOREIGN KEY([AttributeId])
      REFERENCES [dbo].[Attribute] ([AttributeId])
      ON DELETE CASCADE;

      ALTER TABLE [dbo].[AttributeValue] CHECK CONSTRAINT [FK_AttributeValue_Atribute];

      delete from dbo.Attribute where MetaId is null;

      ALTER TABLE [dbo].[AlternativeDef] DROP CONSTRAINT [FK_AlternativeDef_Definition];

      ALTER TABLE [dbo].[AlternativeDef]  WITH CHECK ADD  CONSTRAINT [FK_AlternativeDef_Definition] FOREIGN KEY([MetaId])
      REFERENCES [dbo].[Definition] ([MetaId])
      ON DELETE CASCADE;

      ALTER TABLE [dbo].[AlternativeDef] CHECK CONSTRAINT [FK_AlternativeDef_Definition];

      delete from dbo.AlternativeDef where MetaId is null;
