FME workspace find_right_coordsys.fmw

Parameters:
- SourceDataset_OGCGEOPACKAGE = C:\ny_slask\halland\halmstad_9999\halmstad2017111f.gpkg   # GeoPackage at omprojecera
- TRANSLATION_FILE = $(FME_HOME)Reproject\Gtrans\Sys\halmstad_lokalt_sweref991330.tf   # Gtrans fil
- SOURCE = EPSG:3008   # EnableReadFromFeature:Yes Source Coordinate System

Readers:
- OGCGEOPACKAGE_1: OGCGEOPACKAGE from $(SourceDataset_OGCGEOPACKAGE)

features (reader OGCGEOPACKAGE_1)
    attributes: geom text, object_id mediumint, SymbolId mediumint, GeoObjectId mediumint, spatial_type text, fid int,PrimaryKey
    -> Reprojector
    -> GtransReprojector
GtransReprojector
    INTERPOLATION_TYPE = ,NearestNeighbor
    RASTER_CELL_SIZE_LOOKUP = ,SquareCells
    RASTER_TOLERANCE = 0.0
    TRANSLATION_FILE = $(TRANSLATION_FILE)
    INTERPOLATION_TYPE_NAME = Nearest Neighbor
    RASTER_CELL_SIZE = Square Cells
    REPROJECTED -> Reprojector_3
Reprojector_3
    DEST = EPSG:3006
    INTERPOLATION_TYPE = ,NearestNeighbor
    RASTER_CELL_SIZE_LOOKUP = ,PreserveCells
    RASTER_TOLERANCE = 0.0
    SOURCE = $(SOURCE)
    INTERPOLATION_TYPE_NAME = Nearest Neighbor
    RASTER_CELL_SIZE = Preserve Cells
Reprojector
    DEST = EPSG:3006
    INTERPOLATION_TYPE = ,NearestNeighbor
    RASTER_CELL_SIZE_LOOKUP = ,PreserveCells
    RASTER_TOLERANCE = 0.0
    SOURCE = $(SOURCE)
    INTERPOLATION_TYPE_NAME = Nearest Neighbor
    RASTER_CELL_SIZE = Preserve Cells
