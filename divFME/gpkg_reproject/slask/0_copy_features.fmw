FME workspace 0_copy_features.fmw

Parameters:
- SourceDataset_OGCGEOPACKAGE = C:\ny_slask\test_reproject_gpkg\sau2002334kyrb.gpkg   # GeoPackage File
- DestDataset_OGCGEOPACKAGE = C:\ny_slask\test_reproject_gpkg\sau2002334kyrb_new.gpkg   # GeoPackage File
- DestDataset_SQLITE3 = C:\ny_slask\test_reproject_gpkg\sau2002334kyrb_new.gpkg   # SQLite Database

Readers:
- OGCGEOPACKAGE_1: OGCGEOPACKAGE from $(SourceDataset_OGCGEOPACKAGE)

Writers:
- OGCGEOPACKAGE_2: OGCGEOPACKAGE to $(DestDataset_OGCGEOPACKAGE) in EPSG:2400
- SQLITE3_1: SQLITE3 to $(DestDataset_SQLITE3)

features (reader OGCGEOPACKAGE_1)
    attributes: object_id mediumint, SymbolId mediumint, GeoObjectId mediumint, spatial_type text, fid int,PrimaryKey
    -> features (writer OGCGEOPACKAGE_2)
features (writer OGCGEOPACKAGE_2)
    attributes: object_id mediumint, SymbolId mediumint, GeoObjectId mediumint, spatial_type text, fid int,PrimaryKey
gpkg_geometry_columns (reader OGCGEOPACKAGE_1) [off]
    attributes: table_name text, column_name text, geometry_type_name text, srs_id int, z int, m int
gpkg_contents (reader OGCGEOPACKAGE_1) [off]
    attributes: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
gpkg_geometry_columns (writer SQLITE3_1) [off]
    attributes: table_name text,Unique, column_name text,Unique, geometry_type_name text, srs_id integer, z integer, m integer
gpkg_spatial_ref_sys (writer SQLITE3_1) [off]
    attributes: srs_name text, srs_id integer, organization text, organization_coordsys_id integer, definition text, description text
project_information (writer SQLITE3_1) [off]
    attributes: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
