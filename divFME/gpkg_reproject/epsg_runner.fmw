FME workspace epsg_runner.fmw

Parameters:
- srs_choice = NO   # SRS=9999
- org = C:\ny_slask\upmus_gpkg\rester_kolla_upp\ark8323.gpkg   # "" org Select a File
- SOURCE_srs = EPSG:3021   # EnableReadFromFeature:Yes EPSG Coordinate System
- qgis_bin = C:\Program Files\QGIS 3.34.2\bin   # path QGIS bin

Creator
    GEOMTYPE = Geometry Object
    NUM = 1
    CREATED -> FilenamePartExtractor
FilenamePartExtractor
    DIRNAME_ATTR = _dirname
    DIRPATH_ATTR = _dirpath
    EXTENSION_ATTR = _extension
    FULLNAME_ATTR = _filename
    ROOTNAME_ATTR = _rootname
    SRC_ATTR = $(org)
    -> AttributeManager
AttributeManager
    ATTR_TABLE:
      SET_TO new_gpkg = @Value(_dirpath)reprojected\@Value(_filename)
      SET_TO temp = @Value(_dirpath)temp\@Value(_rootname)_reproject.gpkg
      SET_TO
    USER_EXPOSED_ATTRIBUTES = _creation_instance,_dirpath,_filename,_rootname,_extension,_dirname
    -> SystemCaller
Note: gör features till ett geometrilager
WorkspaceRunner
    BLOCKING = Yes
    WORKSPACE_FILE = $(FME_MF_DIR)wsr\1_make_features_features.fmw
    WORKSPACE_PARAMETERS = SourceDestDataset_SQLITE3,@Value(new_gpkg)
    SUCCEEDED -> WorkspaceRunner_2
Note: projecera om features och project_information
WorkspaceRunner_2
    BLOCKING = Yes
    WORKSPACE_FILE = $(FME_MF_DIR)wsr\2_reprojectEPSG.fmw
    WORKSPACE_PARAMETERS = kopia_SourceDataset_OGCGEOPACKAGE_3,@Value(new_gpkg),reprojectDestDataset_OGCGEOPACKAGE_2,@Value(temp),SOURCE_srs,$(SOURCE_srs)
    SUCCEEDED -> WorkspaceRunner_4
Note: kopiera in de omprojecerade till kopian mha ogr2ogr
WorkspaceRunner_4
    BLOCKING = Yes
    WORKSPACE_FILE = $(FME_MF_DIR)wsr\3_copy_ogr2ogr.fmw
    WORKSPACE_PARAMETERS = kopia_DestDataset_OGCGEOPACKAGE_3,@Value(new_gpkg),reprojectSourceDataset_OGCGEOPACKAGE_2,@Value(temp),qgis_bin,$(qgis_bin)
    SUCCEEDED -> WorkspaceRunner_3
Note: fixa till koordinaterna på vyerna / kopiera metadata / ta bort features som geometri
WorkspaceRunner_3
    BLOCKING = Yes
    WORKSPACE_FILE = $(FME_MF_DIR)wsr\4_fix_gpkg_tables.fmw
    WORKSPACE_PARAMETERS = reproject,@Value(new_gpkg),org_gpkg,$(org)
    SUCCEEDED -> SystemCaller_2
Note: delete temp gpkg
SystemCaller_2
    CMD = del  @Value(temp)

Bookmark: cmd
Note: create folders if not exist / copy gpkg fil
SystemCaller
    CMD = mkdir  @Value(_dirpath)reprojected
    -> SystemCaller_3
SystemCaller_3
    CMD = mkdir  @Value(_dirpath)temp
    -> SystemCaller_4
SystemCaller_4
    CMD = copy $(org) @Value(_dirpath)reprojected\@Value(_filename)   /y
    -> Tester

Bookmark: om SRS är 9999
Note: fix srs 9999
Tester
    BOOL_OP = OR
    TEST_CLAUSE = TEST $(srs_choice) = YES
    TEST_MODE = TEST
    PASSED -> WorkspaceRunner_5
    FAILED -> WorkspaceRunner
WorkspaceRunner_5
    BLOCKING = Yes
    WORKSPACE_FILE = $(FME_MF_DIR_ENCODED)wsr\set_srs_in_gpkg.fmw
    WORKSPACE_PARAMETERS = reproject,@Value(new_gpkg),srs_to_set,-1
    SUCCEEDED -> WorkspaceRunner
