FME workspace runner_gtrans.fmw

Parameters:
- org = C:\ny_slask\SAU_lev2\leverans_orginal_kopia\unknown\enb3032.gpkg   # "" org Select a File
- TRANSLATION_FILE = $(FME_HOME)Reproject\Gtrans\Sys\Norrkoping_RT90-SWEREF991630.tf   # Translation File
- SOURCE_srs = EPSG:3010   # EnableReadFromFeature:Yes EPSG Coordinate System

Creator
    GEOMTYPE = Geometry Object
    NUM = 1
    CREATED -> FilenamePartExtractor
FilenamePartExtractor
    DIRNAME_ATTR = _dirname
    DIRPATH_ATTR = _dirpath
    EXTENSION_ATTR = _extension
    FULLNAME_ATTR = _filename
    ROOTNAME_ATTR = _rootname
    SRC_ATTR = $(org)
    -> AttributeManager
AttributeManager
    ATTR_TABLE:
      SET_TO copy = @Value(_dirpath)reprojected\@Value(_filename)
      SET_TO reproject = @Value(_dirpath)temp\@Value(_rootname)_reproject.gpkg
      SET_TO
    USER_EXPOSED_ATTRIBUTES = _creation_instance,_dirpath,_filename,_rootname,_extension,_dirname
    -> SystemCaller
Note: gör features till ett geometrilager
WorkspaceRunner
    BLOCKING = Yes
    WORKSPACE_FILE = $(FME_MF_DIR)wsr\1_make_features_features.fmw
    WORKSPACE_PARAMETERS = SourceDestDataset_SQLITE3,@Value(copy)
    SUCCEEDED -> WorkspaceRunner_2
Note: projecera om features och project_information
WorkspaceRunner_2
    BLOCKING = Yes
    WORKSPACE_FILE = $(FME_MF_DIR)wsr\2_reproject.fmw
    WORKSPACE_PARAMETERS = kopia_SourceDataset_OGCGEOPACKAGE_3,@Value(copy),reprojectDestDataset_OGCGEOPACKAGE_2,@Value(reproject),SOURCE_srs,$(SOURCE_srs),TRANSLATION_FILE,$(TRANSLATION_FILE)
    SUCCEEDED -> WorkspaceRunner_4
Note: kopiera in de omprojecerade till kopian mha ogr2ogr
WorkspaceRunner_4
    BLOCKING = No
    MAX_TO_BATCH = 1
    WORKSPACE_FILE = $(FME_MF_DIR)wsr\3_copy_ogr2ogr.fmw
    WORKSPACE_PARAMETERS = kopia_SourceDataset_OGCGEOPACKAGE_3,@Value(copy),reprojectDestDataset_OGCGEOPACKAGE_2,@Value(reproject)
    SUCCEEDED -> WorkspaceRunner_3
Note: fixa till koordinaterna på vyerna / kopiera metadata / ta bort features som geometri
WorkspaceRunner_3
    BLOCKING = Yes
    WORKSPACE_FILE = $(FME_MF_DIR)wsr\4_fix_gpkg_tables.fmw
    WORKSPACE_PARAMETERS = DestDataset_SQLITE3,@Value(copy),SourceDataset_SQLITE3_2,$(org),SourceDataset_SQLITE3,C:\ny_slask\test_reproject_gpkg\reprojected\enb3032.gpkg
    SUCCEEDED -> SystemCaller_2
Note: delete temp gpkg
SystemCaller_2
    CMD = del  @Value(reproject)

Bookmark: cmd
Note: create folders if not exist / copy gpkg fil
SystemCaller
    CMD = "mkdir  @Value(_dirpath)reprojected\n"
    -> SystemCaller_3
SystemCaller_3
    CMD = mkdir  @Value(_dirpath)temp
    -> SystemCaller_4
SystemCaller_4
    CMD = copy $(org) @Value(_dirpath)reprojected\@Value(_filename)   /y
    -> WorkspaceRunner
