FME workspace checkIfInBoundingBoxOfCoordSys2.fmw

Parameters:
- HOST_POSTGISserver = uuc-srv390.user.uu.se   # Server
- SourceDataset_POSTGIS_2 = sau2005saga36   # Database
- srid = 3021   # SRID
- USER_NAME_POSTGIS = postgres   # Username
- PASSWORD =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   # Password
- DestDataset_OGCGEOPACKAGE = C:\Users\krima354\Work Folders\Documents\kicki_arbetsfiler\slask\sau2010sta2116.gpkg   # GeoPackage File
- SourceDataset_OGCGEOPACKAGE = C:\Users\krima354\Work Folders\Documents\kicki_arbetsfiler\arkeologiska_uppdrag_grävda_ytor_sverige.gpkg   # GeoPackage File
- LOG_FILE = hej   # Log File

Readers:
- OGCGEOPACKAGE_2: OGCGEOPACKAGE from $(SourceDataset_OGCGEOPACKAGE) in EPSG:3006
- POSTGIS_1: POSTGIS from $(SourceDataset_POSTGIS_2) in EPSG:3006

Writers:
- OGCGEOPACKAGE_1: OGCGEOPACKAGE to $(DestDataset_OGCGEOPACKAGE) in EPSG:3006

GeoObject (reader POSTGIS_1)
    attributes: ObjectId int4, MetaId int4, SymbolId int4, the_raster raster
    -> BoundingBoxAccumulator
BoundingBoxAccumulator
    ACCUM_ATTRS_NAME = Use Attributes From One Feature
    BOUNDING_BOX -> AttributeManager
AttributeManager
    ATTR_TABLE:
      REMOVE ObjectId
      REMOVE MetaId
      REMOVE SymbolId
      REMOVE the_raster
      SET_TO databas = $(SourceDataset_POSTGIS_2)
      SET_TO SRID_intrasis = $(srid)
    -> SpatialFilter_2 [Filter]
    -> intrasis_bb (writer OGCGEOPACKAGE_1)
intrasis_bb (writer OGCGEOPACKAGE_1)
    attributes: databas text(200), SRID_intrasis text(200)
bb_lamning (writer OGCGEOPACKAGE_1)
    attributes: databas text(200), SRID_intrasis text(200), _predicate text, id text(255), uppdragsnummer text(9), beslutande_myndighet text(255), beslutsdatum date, diarienummer text(255), uppdragstyp text(255), utforande_organisation text(255), nollresultat text(9), url text(255), status text(255), lan text, kommun text, socken text

Bookmark: uppdragsnunmmer
arkeologiska_uppdrag_grävda_ytor_sverige_linestring (reader OGCGEOPACKAGE_2)
    attributes: id text(255), uppdragsnummer text(9), beslutande_myndighet text(255), beslutsdatum date, diarienummer text(255), uppdragstyp text(255), utforande_organisation text(255), nollresultat text(9), url text(255), status text(255), lan text, kommun text, socken text, fid int,PrimaryKey
    -> SpatialFilter_2 [Candidate]
arkeologiska_uppdrag_grävda_ytor_sverige_point (reader OGCGEOPACKAGE_2)
    attributes: id text(255), uppdragsnummer text(9), beslutande_myndighet text(255), beslutsdatum date, diarienummer text(255), uppdragstyp text(255), utforande_organisation text(255), nollresultat text(9), url text(255), status text(255), lan text, kommun text, socken text, fid int,PrimaryKey
    -> SpatialFilter_2 [Candidate]
arkeologiska_uppdrag_grävda_ytor_sverige_polygon (reader OGCGEOPACKAGE_2)
    attributes: id text(255), uppdragsnummer text(9), beslutande_myndighet text(255), beslutsdatum date, diarienummer text(255), uppdragstyp text(255), utforande_organisation text(255), nollresultat text(9), url text(255), status text(255), lan text, kommun text, socken text, fid int,PrimaryKey
    -> SpatialFilter_2 [Candidate]
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeManager_2
AttributeManager_2
    ATTR_TABLE = REMOVE fid
    -> bb_lamning (writer OGCGEOPACKAGE_1)
