FME workspace checkSRIDfromIntrasis_runner.fmw

Parameters:
- HOST_POSTGISserver = uuc-srv390.user.uu.se   # Server
- PORT = 5433   # Port
- USER_NAME_POSTGIS = postgres   # Username
- DestDataset_CSV2 = C:\Users\krima354\Work Folders\Documents\kicki_arbetsfiler\slask   # Destination CSV (Comma Separated Value) Folder
- SourceDataset_CSV2_3 = C:\Users\krima354\Box\Urdar\uuid_check\archive_in wrong_place.csv   # Source CSV (Comma Separated Value) File(s)
- SourceDataset_PATH = C:\Users\krima354\Work Folders\Documents\kicki_arbetsfiler\slask\alla_gpkg_csv_20240117   # INCLUDE_WEB_BROWSER Source Folder and File Pathnames Folder

Readers:
- CSV2_2: CSV2 from $(SourceDataset_CSV2_3)
- PATH_1: PATH from $(SourceDataset_PATH)

Note: urdardb
CSV (reader CSV2_2) [off]
    attributes: intrasisarchive varchar(11), var_test varchar(12), var varchar(26), uuid varchar(37), fel varchar(99), UUIDkorrekt varchar(23), col6 varchar(77)
PATH (reader PATH_1)
    attributes: path_unix buffer, path_windows buffer, path_rootname buffer, path_filename buffer, path_extension buffer, path_directory_unix buffer, path_directory_windows buffer, path_type char(10)
    -> AttributeManager
AttributeManager
    ATTR_TABLE = RENAME_SET_VALUE path_rootname > intrasisarchive
    -> WorkspaceRunner
WorkspaceRunner
    BLOCKING = Yes
    WORKSPACE_FILE = $(FME_MF_DIR)checkSRIDfromIntrasis.fmw
    WORKSPACE_PARAMETERS = SourceDataset_POSTGIS_2,@Value(intrasisarchive),HOST_POSTGISserver,$(HOST_POSTGISserver),USER_NAME_POSTGIS,$(USER_NAME_POSTGIS),PORT,$(PORT),DestDataset_CSV2,$(DestDataset_CSV2)
