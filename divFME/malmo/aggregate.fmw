FME workspace aggregate.fmw

Parameters:
- DestDataset_OGCGEOPACKAGE = C:\ny_slask\mm_aldre_filer\wetransfer_overforing-mm_1_2025-11-20_1159\geodata\alla_txt_reproject.gpkg   # GeoPackage File dest agg
- SourceDataset_OGCGEOPACKAGE_3 = C:\ny_slask\mm_aldre_filer\wetransfer_overforing-mm_1_2025-11-20_1159\geodata\Inmätningsfiler Öresundsförbindelsen_MM\Fortuna 17A-B_MHM 9147, 9148\raw\raw_data_bearbetat_reprojected.gpkg   # GeoPackage File
- FEATURE_TYPES =

Readers:
- OGCGEOPACKAGE_2: OGCGEOPACKAGE from $(SourceDataset_OGCGEOPACKAGE_3)

Writers:
- OGCGEOPACKAGE_1: OGCGEOPACKAGE to $(DestDataset_OGCGEOPACKAGE)

prov_point (reader OGCGEOPACKAGE_2)
    attributes: obj_nr text(200), typ text(200), kod text, y text, x text, z text, antal_punkter int, id int,PrimaryKey
    -> AttributeManager
AttributeManager
    ATTR_TABLE = SET_TO fil (varchar(200)) = $(SourceDataset_OGCGEOPACKAGE_3)
    -> geometrier (writer OGCGEOPACKAGE_1)
geometrier (writer OGCGEOPACKAGE_1)
    attributes: kod text, fil text(200), y text, x text, z text, obj_nr text(200), typ text(200), antal_punkter int
