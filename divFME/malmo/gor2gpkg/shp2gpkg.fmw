FME workspace shp2gpkg.fmw

Parameters:
- SourceDataset_SHAPEFILE = C:\ny_slask\mm_aldre_filer\wetransfer_overforing-mm_1_2025-11-20_1159\Inmätningsfiler Öresundsförbindelsen_MM\Södra Sallerup 15C och A_MHM 9140, 9113\MHM 9140\09140_sallerup_15c.shp   # Source Esri Shapefile(s)
- FEATURE_TYPES =
- DestDataset_OGCGEOPACKAGE = C:\ny_slask\mm_aldre_filer\wetransfer_overforing-mm_1_2025-11-20_1159\Inmätningsfiler Öresundsförbindelsen_MM\Södra Sallerup 15C och A_MHM 9140, 9113\MHM 9140\shp_data.gpkg   # GeoPackage File

Readers:
- SHAPEFILE_1: SHAPEFILE from $(SourceDataset_SHAPEFILE)

Writers:
- OGCGEOPACKAGE_1: OGCGEOPACKAGE to $(DestDataset_OGCGEOPACKAGE)

09149 (reader SHAPEFILE_1)
    attributes: ENTITY varchar(14)
    -> Table1 (writer OGCGEOPACKAGE_1)
Table1 (writer OGCGEOPACKAGE_1)
