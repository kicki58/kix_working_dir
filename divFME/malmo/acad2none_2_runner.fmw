FME workspace acad2none_2_runner.fmw

Parameters:
- SourceDataset_PATH = \\argos.storage.uu.se\MyFolder$\krima354\kicki_arbetsfiler\mm_aldre_filer\wetransfer_overforing-mm_1_2025-11-20_1159\Inmätningsfiler Öresundsförbindelsen_MM   # INCLUDE_WEB_BROWSER Source Folder and File Pathnames Folder
- MAX_FEATURES =   # Max Features to Read

Readers:
- PATH_1: PATH from $(SourceDataset_PATH)

PATH (reader PATH_1)
    attributes: path_unix buffer, path_windows buffer, path_rootname buffer, path_filename buffer, path_extension buffer, path_directory_unix buffer, path_directory_windows buffer, path_type char(10)
    -> AttributeManager
AttributeManager
    ATTR_TABLE:
      RENAME_SET_VALUE path_windows > dxf_fil (buffer)
      SET_TO gpkg (varchar(200)) = @Value(path_directory_windows)data.gpkg
    -> WorkspaceRunner
WorkspaceRunner
    BLOCKING = Yes
    OVERWRITE_LOG_FILE = HONOR
    STDERR_HANDLING = COMBINE
    WORKSPACE_FILE = $(FME_MF_DIR_ENCODED)acad2none_2.fmw
    WORKSPACE_PARAMETERS = SourceDataset_ACAD,@Value(dxf_fil),DestDataset_OGCGEOPACKAGE,@Value(gpkg)
