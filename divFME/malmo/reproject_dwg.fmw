FME workspace reproject_dwg.fmw

Parameters:
- SourceDataset_OGCGEOPACKAGE = C:\ny_slask\mm_aldre_filer\wetransfer_overforing-mm_1_2025-11-20_1159\geodata\Inmätningsfiler Öresundsförbindelsen_MM\Sunnanå 19A-F_MHM 9151-9156\MHM 9151\xyz\xyz_data_bearbetat.gpkg   # GeoPackage File
- FEATURE_TYPES =
- DestDataset_OGCGEOPACKAGE = C:\ny_slask\mm_aldre_filer\wetransfer_overforing-mm_1_2025-11-20_1159\geodata\Inmätningsfiler Öresundsförbindelsen_MM\Sunnanå 19A-F_MHM 9151-9156\MHM 9151\xyz\xyz_data_bearbetat_reprojected.gpkg   # GeoPackage File

Readers:
- OGCGEOPACKAGE_1: OGCGEOPACKAGE from $(SourceDataset_OGCGEOPACKAGE)

Writers:
- OGCGEOPACKAGE_2: OGCGEOPACKAGE to $(DestDataset_OGCGEOPACKAGE)

point (reader OGCGEOPACKAGE_1)
    attributes: kod text, y text, x text, z text, antal int, _element_index int, id int,PrimaryKey
    -> Tester
Tester
    BOOL_OP = OR
    TEST_CLAUSE = TEST @Value(x) > 30000
    TEST_MODE = TEST
    PASSED -> Offsetter
    FAILED -> GtransReprojector
Offsetter
    MODE_LOOKUP = CARTESIAN
    XOFF = -300000
    YOFF = -300000
    ZOFF = 0
    MODE = Cartesian Coordinate
    OFFSET -> GtransReprojector
GtransReprojector
    INTERPOLATION_TYPE = ,NearestNeighbor
    RASTER_CELL_SIZE_LOOKUP = ,SquareCells
    RASTER_TOLERANCE = 0.0
    TRANSLATION_FILE = $(FME_HOME)Reproject\Gtrans\Sys\MSBL_lok-SW991330.tf
    INTERPOLATION_TYPE_NAME = Nearest Neighbor
    RASTER_CELL_SIZE = Square Cells
    REPROJECTED -> Reprojector
Reprojector
    DEST = EPSG:3006
    INTERPOLATION_TYPE = NearestNeighbor
    RASTER_CELL_SIZE = PreserveCells
    RASTER_TOLERANCE = 0.0
    SOURCE = EPSG:3008
    REPROJECTED -> Table1 (writer OGCGEOPACKAGE_2)
Table1 (writer OGCGEOPACKAGE_2)
