FME workspace runAll2gpkg.fmw

Creator
    GEOMTYPE = Geometry Object
    NUM = 1
    CREATED -> WorkspaceRunner
Note: dat2gpkg
WorkspaceRunner
    BLOCKING = Yes
    OVERWRITE_LOG_FILE = HONOR
    STDERR_HANDLING = COMBINE
    WORKSPACE_FILE = $(FME_MF_DIR_ENCODED)dat2gpkg_runner.fmw
    WORKSPACE_PARAMETERS = SourceDataset_PATH,C:\ny_slask\mm_aldre_filer\wetransfer_overforing-mm_1_2025-11-20_1159\geodata,MAX_FEATURES,
    SUCCEEDED -> WorkspaceRunner_2
Note: dbase2gpkg
WorkspaceRunner_2
    BLOCKING = Yes
    OVERWRITE_LOG_FILE = HONOR
    STDERR_HANDLING = COMBINE
    WORKSPACE_FILE = $(FME_MF_DIR_ENCODED)dbase2gpkg_runner.fmw
    WORKSPACE_PARAMETERS = SourceDataset_PATH,C:\ny_slask\mm_aldre_filer\wetransfer_overforing-mm_1_2025-11-20_1159\geodata,MAX_FEATURES,
    SUCCEEDED -> WorkspaceRunner_3
Note: dxf2gpkg
WorkspaceRunner_3
    BLOCKING = Yes
    OVERWRITE_LOG_FILE = HONOR
    STDERR_HANDLING = COMBINE
    WORKSPACE_FILE = $(FME_MF_DIR_ENCODED)dxf2gpkg_runner.fmw
    WORKSPACE_PARAMETERS = SourceDataset_PATH,C:\ny_slask\mm_aldre_filer\wetransfer_overforing-mm_1_2025-11-20_1159\geodata,MAX_FEATURES,
    SUCCEEDED -> WorkspaceRunner_4
Note: job2gpkg
WorkspaceRunner_4
    BLOCKING = Yes
    OVERWRITE_LOG_FILE = HONOR
    STDERR_HANDLING = COMBINE
    WORKSPACE_FILE = $(FME_MF_DIR_ENCODED)job2gpkg_runner.fmw
    WORKSPACE_PARAMETERS = SourceDataset_PATH,C:\ny_slask\mm_aldre_filer\wetransfer_overforing-mm_1_2025-11-20_1159\geodata,MAX_FEATURES,
    SUCCEEDED -> WorkspaceRunner_5
Note: shp2gpkg
WorkspaceRunner_5
    BLOCKING = Yes
    OVERWRITE_LOG_FILE = HONOR
    STDERR_HANDLING = COMBINE
    WORKSPACE_FILE = $(FME_MF_DIR_ENCODED)shp2gpkg_runner.fmw
    WORKSPACE_PARAMETERS = SourceDataset_PATH,C:\ny_slask\mm_aldre_filer\wetransfer_overforing-mm_1_2025-11-20_1159\geodata,MAX_FEATURES,
    SUCCEEDED -> WorkspaceRunner_6
Note: txt2gpkg
WorkspaceRunner_6
    BLOCKING = Yes
    OVERWRITE_LOG_FILE = HONOR
    STDERR_HANDLING = COMBINE
    WORKSPACE_FILE = $(FME_MF_DIR_ENCODED)txt2gpkg_runner.fmw
    WORKSPACE_PARAMETERS = SourceDataset_PATH,C:\ny_slask\mm_aldre_filer\wetransfer_overforing-mm_1_2025-11-20_1159\geodata,MAX_FEATURES,
    SUCCEEDED -> WorkspaceRunner_7
Note: xyz2gpkg
WorkspaceRunner_7
    BLOCKING = Yes
    OVERWRITE_LOG_FILE = HONOR
    STDERR_HANDLING = COMBINE
    WORKSPACE_FILE = $(FME_MF_DIR_ENCODED)xyz2gpkg_runner.fmw
    WORKSPACE_PARAMETERS = SourceDataset_PATH,C:\ny_slask\mm_aldre_filer\wetransfer_overforing-mm_1_2025-11-20_1159\geodata,MAX_FEATURES,
    SUCCEEDED -> WorkspaceRunner_8
Note: raw2gpkg
WorkspaceRunner_8
    BLOCKING = Yes
    OVERWRITE_LOG_FILE = HONOR
    STDERR_HANDLING = COMBINE
    WORKSPACE_FILE = $(FME_MF_DIR_ENCODED)raw2gpkg_runner.fmw
    WORKSPACE_PARAMETERS = SourceDataset_PATH,C:\ny_slask\mm_aldre_filer\wetransfer_overforing-mm_1_2025-11-20_1159\geodata,MAX_FEATURES,
