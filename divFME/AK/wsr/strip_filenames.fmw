FME workspace strip_filenames.fmw

Parameters:
- SourceDataset_PATH = C:\Github\kix\SiteWorks-Py\result\2886 Drakegården   # INCLUDE_WEB_BROWSER Source Folder and File Pathnames Folder

Readers:
- PATH_1: PATH from $(SourceDataset_PATH)

Writers:
- FILECOPY_1: FILECOPY to $(SourceDataset_PATH)

PATH (reader PATH_1)
    attributes: path_unix buffer, path_windows buffer, path_rootname buffer, path_filename buffer, path_extension buffer, path_directory_unix buffer, path_directory_windows buffer, path_type char(10)
    -> AttributeManager
AttributeManager
    ATTR_TABLE:
      SET_TO filecopy_dest_filename = @Value(path_directory_windows)
      SET_TO position_of_ = @FindString(@Value(path_rootname),"_",0,caseSensitive=TRUE)
    -> AttributeManager_3
AttributeManager_3
    ATTR_TABLE:
      RENAME_SET_VALUE path_windows > filecopy_source_dataset
      SET_TO filecopy_dest_filename = @Substring(@Value(path_rootname),0,@Value(position_of_)).csv
      SET_TO
    -> AttributeRemover
AttributeRemover
    REMOVE_ATTRS = path_directory_unix,path_extension,path_filename,path_type,path_unix,path_rootname,position_of_
    -> csv (writer FILECOPY_1)
csv (writer FILECOPY_1)
