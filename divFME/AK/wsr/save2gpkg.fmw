FME workspace save2gpkg.fmw
Startup Python:
      import fmeobjects

Parameters:
- project_folder = C:\Github\kix\SiteWorks-Py\result   # Select a Folder with CSV
- db_name = 2939_genv   # db namn
- dest_folder = C:\Github\kix\SiteWorks-Py\gpkg_20250325   # Destination folder
- DestDataset_OGCGEOPACKAGE = $(dest_folder)\$(db_name).gpkg   # GeoPackage File
- SourceDataset_CSV2_43 = $(project_folder)\$(db_name)\csv\OBJDATA.csv   # Source CSV OBJDATA
- SourceDataset_CSV2_59 = $(project_folder)\$(db_name)\csv\OBJ.csv   # Source CSV OBJ
- SourceDataset_CSV2_63 = $(project_folder)\$(db_name)\csv\OBJDETAILS.csv   # Source CSV OBJDETAILS
- SourceDataset_CSV2_46 = $(project_folder)\$(db_name)\csv\PROJECT.csv   # Source CSV PROJECT
- SourceDataset_XLSXR = $(FME_MF_DIR_USERTYPED)metadatamallen_sw.xlsx   # Source Microsoft Excel File(s)
- SourceDataset_CSV2 = $(project_folder)\$(db_name)\csv\RELATIONS.csv   # Source CSV RELATIONS

Readers:
- CSV2_16: CSV2 from $(SourceDataset_CSV2_59)
- CSV2_17: CSV2 from $(SourceDataset_CSV2_63)
- CSV2_24: CSV2 from $(SourceDataset_CSV2_46)
- CSV2_12: CSV2 from $(SourceDataset_CSV2_43)
- PATH_1: PATH from C:\Github\kix\SiteWorks-Py\result
- XLSXR_1: XLSXR from $(SourceDataset_XLSXR)
- CSV2_1: CSV2 from $(SourceDataset_CSV2)

Writers:
- OGCGEOPACKAGE_1: OGCGEOPACKAGE to $(DestDataset_OGCGEOPACKAGE)
- SQLITE3_2: SQLITE3 to $(DestDataset_OGCGEOPACKAGE)

Bookmark: fixfix geom
Note: CSV: OBJDATA [CSV2] / geometrier
CSV (reader CSV2_12)
    attributes: SEQNO uint32, X x_coordinate, Y y_coordinate, Z z_coordinate, OBJECTID uint32
    -> VertexCreator
VertexCreator
    MEASURE_TYPE_LOOKUP = CONTINUOUS
    MODE = REPLACE
    XVAL = @Value(X)
    YVAL = @Value(Y)
    ZVAL = @Value(Z)
    MEASURE_TYPE = Continuous
    MODE_NAME = Replace with Point
    -> Sorter
    -> Aggregator
Sorter
    GROUP_BY = OBJECTID
    SORT_PARM = SEQNO NATURAL ASCENDING
    SORTED -> LineBuilder_2
LineBuilder_2
    ACCUM_INPUT_ATTRS = Use Attributes From One Feature
    GROUP_BY = OBJECTID
    REMOVE_DUPLICATES_LOOKUP = NO
    REMOVE_DUPLICATES = No
    POINT -> FeatureMerger_2 [REQUESTOR]
    LINE -> FeatureMerger_2 [REQUESTOR]
    POLYGON -> FeatureMerger_2 [REQUESTOR]
Note: CSV: OBJDETAILS [CSV2]
CSV (reader CSV2_17)
    attributes: PROJECT string, CATEGORY string, OBJECTNO string, SUBOBJECT string, COLOUR string, TECHNIQUE string, WEARMARKS string, PROCESSES string, DECORATION string, SHAPE string, S1 string, S2 string, S3 string, S4 string, S5 string, S6 string, OBJECTID string, IDX string
    -> AttributeManager_7
AttributeManager_7
    ATTR_TABLE = SET_TO OBJECTNO_SUBOBJECT_IDX (varchar(200)) = FME_CONDITIONAL:DEFAULT_VALUE'@Value(OBJECTNO)_@Value(SUBOBJECT)'BOOL_OP;OR;COMPOSITE_TEST;1;TEST IDX ATTRIBUTE_HAS_A_VALUE _FME_BLANK_STRING_'@Value(OBJECTNO)_@Value(SUBOBJECT)_@Value(IDX)'FME_NUM_CONDITIONS2___
    -> object_details (writer SQLITE3_2)
object_details (writer SQLITE3_2)
    attributes: PROJECT text, CATEGORY text, OBJECTNO text, SUBOBJECT text, COLOUR text, TECHNIQUE text, WEARMARKS text, PROCESSES text, DECORATION text, SHAPE text, S1 text, S2 text, S3 text, S4 text, S5 text, S6 text, OBJECTID text, IDX text, OBJECTNO_SUBOBJECT_IDX text
Note: CSV: OBJ [CSV2]
CSV (reader CSV2_16)
    attributes: PROJECT uint32, CATEGORY varchar(12), OBJECTNO uint32, SUBOBJECT uint32, TYPENO uint32, DESCRIPTION varchar(1), SUBCLASS varchar(1), DEFINITION varchar(1), INTERPRETATIONS varchar(192), X_AVG x_coordinate, Y_AVG y_coordinate, Z_AVG z_coordinate, OBJLENGTH varchar(1), WIDTH varchar(1), NUMBEROF uint32, WEIGHT varchar(1), BELONGSTO uint32, BELONGSTOSUB uint32, BELONGSTOTYPE varchar(8), CONTEXT varchar(1), CONTEXTOBJECT varchar(1), CONTEXTSUBOBJECT varchar(1), CONTEXTTYPE varchar(1), INCLINATION varchar(1), DATEOFRECORDING datetime, MPRECISION varchar(1), SIGN varchar(33), DATING varchar(1), DATING_MARGINOFERROR varchar(1), DATINGMETHOD varchar(1),
      NONMEASUREDLOCATION varchar(1), MEASUREMENTFILE varchar(16), STRUCKOFF varchar(2), CONSTRUCTION uint32, SUBCONSTRUCTION uint32, ORIENTATION varchar(1), FORM varchar(1), COURNERS varchar(1), HEIGHT varchar(1), RIM varchar(1), BOTTOMRIM varchar(1), BOTTOM varchar(1), SECTION varchar(1), CONDITION varchar(1), SPLITTING varchar(1), TOOLTRACES varchar(1), ASSEMBLY varchar(1), MATERIAL varchar(1), GRANULARITY varchar(1), SURFACE varchar(1), JOINTINGMATERIAL varchar(1), SORTING varchar(1), STRUCTURE varchar(1), CONTENTS varchar(1), CONSISTENCE varchar(1), PACKING varchar(1), COLOUR varchar(1), COMPOSITION varchar(1), JOINTING varchar(1), CHALK varchar(1),
      COAL varchar(1), PEBBELS varchar(1), BRICKFRAG varchar(1), BRICK varchar(1), WOOD varchar(1), CLAY varchar(1), BURNT_CLAY varchar(1), DAUB varchar(1), GRAVEL varchar(1), SOOT varchar(1), ASHES varchar(1), ANIMALBONES varchar(1), FISHBONES varchar(1), ROCKS varchar(1), HUMUS varchar(1), BURNT_BONE varchar(1), UNBURNT_BONE varchar(1), FIRE_CRACKED_ROCK varchar(1), BURNT_STONE varchar(1), MACHINE varchar(1), SHOVEL varchar(1), HOETABLE varchar(1), TROWEL varchar(1), SIEVE varchar(1), PREPARATION varchar(1), CONTAMINATION varchar(1), DROUGHT varchar(1), RAIN varchar(1), FROST varchar(1), WATERSIEVE varchar(1),
      RECORDEDBY varchar(1), VERIFIED varchar(1), OBSERVATIONS varchar(4), CONTACT_ABOVE varchar(1), CONTACT_BELOW varchar(1), SIDE varchar(1), LIMITS varchar(1), MAXHEIGHT varchar(1), DETAILS varchar(1), TAQ varchar(1), TPQ varchar(1), STRATATOP varchar(1), STRATABOTTOM varchar(1), SAND varchar(1), LIME varchar(1), PREV_FUNCTION varchar(1), DATEEDITED datetime, BLAZINGCOLOR varchar(1), FILLING varchar(1), TIERS varchar(1), TIER_DEPTH varchar(1), OBJECTID uint32, BELONGSTOID uint32, CONST_PHASE varchar(1), DEST_PHASE varchar(1), AREA real64, SILT varchar(1), ORGANIC_MATTER varchar(1), BOULDERS varchar(1), NOTES varchar(4),
      IDX uint32, TYPENAME varchar(22), CLASS varchar(11), CONT_CLASS varchar(1), DIAMETER varchar(1), PART varchar(1), INNER_LENGTH varchar(1), INNER_WIDTH varchar(1), INNER_HEIGHT varchar(1), SECTIONS varchar(1), EXAMINATION varchar(1), THICKNESS varchar(1), FRAGMENTS varchar(1)
    -> AttributeManager_6
AttributeManager_6
    ATTR_TABLE = SET_TO OBJECTNO_SUBOBJECT_IDX (varchar(200)) = FME_CONDITIONAL:DEFAULT_VALUE'@Value(OBJECTNO)_@Value(SUBOBJECT)'BOOL_OP;OR;COMPOSITE_TEST;1;TEST IDX ATTRIBUTE_HAS_A_VALUE _FME_BLANK_STRING_'@Value(OBJECTNO)_@Value(SUBOBJECT)_@Value(IDX)'FME_NUM_CONDITIONS2___
    -> AttributeKeeper
    -> rtfAll2 [AttributeKeeper_Input]
    -> FeatureMerger_5 [REQUESTOR]
AttributeKeeper
    CREATE_BULK_MODE_FEATURES = NO
    KEEP_ATTRS = OBJECTID,OBJECTNO,TYPENO,CLASS,SUBOBJECT,OBJECTNO_SUBOBJECT_IDX,IDX
    -> FeatureMerger_2 [SUPPLIER]
FeatureMerger_2
    ATTR_ACCUM_MODE = Merge Supplier
    ATTR_CONFLICT_RES_LOOKUP = REQUESTOR_IF_CONFLICT
    IGNORE_NULLS = No
    JOIN_KEYS = @Value(OBJECTID) @Value(OBJECTID) AUTO
    MERGE_TYPE = Attributes Only
    PRESERVE_FEATURE_ORDER_LOOKUP = PER_OUTPUT_PORT
    PROCESS_DUPS = NO
    REJECT_NULL_MISSING_KEYS = No
    SUPPLIERS_FIRST = No
    ATTR_CONFLICT_RES = Use Requestor
    MERGED -> TestFilter_2
TestFilter_2
    DEFAULT_VALUE = <UNFILTERED>
    PASSED_TEST_GROUP_OUTPUT = FIRST
    TEST_LIST = "BOOL_OP,OR,COMPOSITE_TEST,""""""1"""""",TEST_CLAUSE,TEST TYPENO ATTRIBUTE_HAS_A_VALUE """,TYPENO ATTRIBUTE_HAS_A_VALUE
    TYPENO ATTRIBUTE_HAS_A_VALUE -> FeatureMerger_3 [REQUESTOR]
rtfAll2
    INTERPRETATIONS = @Value(INTERPRETATIONS)
    NOTES = @Value(NOTES)
    OBJECTID = @Value(OBJECTID)
    OBSERVATIONS = @Value(OBSERVATIONS)
    AttributeManager_5_Output -> FeatureMerger_5 [SUPPLIER]
FeatureMerger_5
    ATTR_ACCUM_MODE = Merge Supplier
    ATTR_CONFLICT_RES_LOOKUP = SUPPLIER_IF_CONFLICT
    IGNORE_NULLS = No
    JOIN_KEYS = @Value(OBJECTID) @Value(OBJECTID) AUTO
    MERGE_TYPE = Attributes Only
    PROCESS_DUPS = NO
    REJECT_NULL_MISSING_KEYS = No
    SUPPLIERS_FIRST = No
    ATTR_CONFLICT_RES = Use Supplier
    MERGED -> objects (writer SQLITE3_2)
objects (writer SQLITE3_2)
    attributes: DATEOFRECORDING text, DATEEDITED text, X_AVG double, Y_AVG double, Z_AVG double, AREA double, PROJECT integer, OBJECTNO integer, SUBOBJECT integer, TYPENO integer, NUMBEROF integer, BELONGSTO integer, BELONGSTOSUB integer, CONSTRUCTION integer, SUBCONSTRUCTION integer, OBJECTID integer, BELONGSTOID integer, IDX integer, BOULDERS text, NOTES text, TYPENAME text, CLASS text, CONT_CLASS text, DIAMETER text, PART text, INNER_LENGTH text, INNER_WIDTH text, INNER_HEIGHT text, SECTIONS text, EXAMINATION text,
      THICKNESS text, FRAGMENTS text, CATEGORY text, DESCRIPTION text, SUBCLASS text, DEFINITION text, INTERPRETATIONS text, OBJLENGTH text, WIDTH text, WEIGHT text, BELONGSTOTYPE text, CONTEXT text, CONTEXTOBJECT text, CONTEXTSUBOBJECT text, CONTEXTTYPE text, INCLINATION text, MPRECISION text, SIGN text, DATING text, DATING_MARGINOFERROR text, DATINGMETHOD text, NONMEASUREDLOCATION text, MEASUREMENTFILE text, STRUCKOFF text, ORIENTATION text, FORM text, COURNERS text, HEIGHT text, RIM text, BOTTOMRIM text,
      BOTTOM text, SECTION text, CONDITION text, SPLITTING text, TOOLTRACES text, ASSEMBLY text, MATERIAL text, GRANULARITY text, SURFACE text, JOINTINGMATERIAL text, SORTING text, STRUCTURE text, CONTENTS text, CONSISTENCE text, PACKING text, COLOUR text, COMPOSITION text, JOINTING text, CHALK text, COAL text, PEBBELS text, BRICKFRAG text, BRICK text, WOOD text, CLAY text, BURNT_CLAY text, DAUB text, GRAVEL text, SOOT text, ASHES text,
      ANIMALBONES text, FISHBONES text, ROCKS text, HUMUS text, BURNT_BONE text, UNBURNT_BONE text, FIRE_CRACKED_ROCK text, BURNT_STONE text, MACHINE text, SHOVEL text, HOETABLE text, TROWEL text, SIEVE text, PREPARATION text, CONTAMINATION text, DROUGHT text, RAIN text, FROST text, WATERSIEVE text, RECORDEDBY text, VERIFIED text, OBSERVATIONS text, CONTACT_ABOVE text, CONTACT_BELOW text, SIDE text, LIMITS text, MAXHEIGHT text, DETAILS text, TAQ text, TPQ text,
      STRATATOP text, STRATABOTTOM text, SAND text, LIME text, PREV_FUNCTION text, BLAZINGCOLOR text, FILLING text, TIERS text, TIER_DEPTH text, CONST_PHASE text, DEST_PHASE text, SILT text, ORGANIC_MATTER text, OBJECTNO_SUBOBJECT_IDX text
hela metadatamallen export (reader XLSXR_1)
    attributes: Version number(2,0), FieldName char(17), DisplayLabel char(20), FieldType char(8), FieldClass char(7), TYPENR number(4,0), MAP char(10), CATEGORYCODE char(3), CATEGORY char(12), CLASS char(28), TYPENAME char(28), CODE char(3), geometri char(8), ELEMENT_TYPE number(2,0), CONT_CLASS string, SYMBOLSIZE number(4,0), SYMBOLTYPE number(2,0), MODULE string, isactproj string, LEVELNO number(2,0), VIEWTYPE number(2,0), ASCKONF number(2,0), COLOR number(2,0), WEIGHT number(2,0), STYLE number(2,0), FILL number(2,0), CLOSED number(2,0), PATTERN_TYPE number(3,0), PATTERN_CELLNAME char(5), ANGLE number(2,0),
      DIST number(2,0), XANGLE number(2,0), XDIST number(2,0), SCALE_PATTERN number(2,0), TEXT number(2,0), TEXT_LEVEL number(2,0), TEXT_SIZE number(3,1), TEXT_FONT number(3,0), TAG number(2,0), PLACECELLROTATE number(2,0), PLACECELLSCALE number(2,0), S1 char(16), S2 char(12), S3 char(5), S4 char(7), S5 char(6), S6 string, S7 string, S8 string, S9 string, S10 string
    -> AttributeKeeper_2
AttributeKeeper_2
    CREATE_BULK_MODE_FEATURES = NO
    KEEP_ATTRS = TYPENR,geometri,TYPENAME
    -> TestFilter_3
TestFilter_3
    DEFAULT_VALUE = <UNFILTERED>
    PASSED_TEST_GROUP_OUTPUT = FIRST
    TEST_LIST = "BOOL_OP,OR,COMPOSITE_TEST,""""""1"""""",TEST_CLAUSE,TEST TYPENAME ATTRIBUTE_HAS_A_VALUE """,TYPENAME ATTRIBUTE_HAS_A_VALUE
    TYPENAME ATTRIBUTE_HAS_A_VALUE -> FeatureMerger_3 [SUPPLIER]
FeatureMerger_3
    ATTR_ACCUM_MODE = Merge Supplier
    ATTR_CONFLICT_RES_LOOKUP = REQUESTOR_IF_CONFLICT
    IGNORE_NULLS = No
    JOIN_KEYS = @Value(TYPENO) @Value(TYPENR) AUTO
    MERGE_TYPE = Attributes Only
    PRESERVE_FEATURE_ORDER_LOOKUP = PER_OUTPUT_PORT
    PROCESS_DUPS = NO
    REJECT_NULL_MISSING_KEYS = No
    SUPPLIERS_FIRST = No
    ATTR_CONFLICT_RES = Use Requestor
    MERGED -> AttributeFilter
AttributeFilter
    ATTR_NAME = geometri
    ATTR_VALUES = <Empty>,<Missing>,<Null>,<Unfiltered>,linje?,polygon,punkt,punkt?,linje
    PRESERVE_FEATURE_ORDER_LOOKUP = PER_OUTPUT_PORT
    linje? -> AttributeManager_5
    polygon -> LineCloser
    punkt -> AttributeManager_5
    punkt? -> AttributeManager_5
    linje -> AttributeManager_5
LineCloser
    CONNECT_Z_MODE_LOOKUP = FIRST_WINS
    CONNECT_Z_MODE = First Wins
    AREA -> AttributeManager_5
AttributeManager_5
    ATTR_TABLE:
      REMOVE SEQNO
      REMOVE X
      REMOVE Y
      REMOVE Z
      REMOVE TYPENO
      REMOVE TYPENR
    -> features (writer OGCGEOPACKAGE_1)
features (writer OGCGEOPACKAGE_1)
    attributes: OBJECTID int, OBJECTNO int, CLASS text, geometri text, SUBOBJECT int, OBJECTNO_SUBOBJECT_IDX text, TYPENAME text, IDX text

Bookmark: project_information
Aggregator
    ACCUM_ATTRS_NAME = Drop Incoming Attributes
    AGGREGATE_TYPE = Heterogeneous Collection
    MODE = Geometry - Assemble One Level
    SEP = ,
    AGGREGATE -> CenterPointExtractor
CenterPointExtractor
    CENTX = _inside_x
    CENTY = _inside_y
    CENTZ = _inside_z
    EXTRACTIONMODE = CENTEROFGRAV
    -> VertexCreator_2
VertexCreator_2
    MEASURE_TYPE_LOOKUP = CONTINUOUS
    MODE = REPLACE
    XVAL = @Value(_inside_x)
    YVAL = @Value(_inside_y)
    ZVAL = @Value(_inside_z)
    MEASURE_TYPE = Continuous
    MODE_NAME = Replace with Point
    -> FeatureMerger_4 [SUPPLIER]
Note: CSV: PROJECT [CSV2]
CSV (reader CSV2_24)
    attributes: PROJECT uint32, OFFICALDESIGNATION varchar(1), PROJECTNAME varchar(1), CLIENT varchar(1), PREMISES varchar(1), PARISH varchar(1), MONUMENT varchar(1), MUNICIPALITY varchar(1), COUNTY varchar(1), PROVINCE varchar(1), BASEMAP varchar(1), PROJECTMANAGER varchar(1), PARTICIPANTS varchar(1), TYPEOFPROJECT varchar(18), STARTOFPROJECT varchar(1), ENDOFPROJECT varchar(1), MANHOURS varchar(1), MACHINEHOURS varchar(1), AREAOFINVEST varchar(1), COORDINATESYST varchar(12), HEIGHTSYST varchar(1), MASL varchar(1), R1 uint32, R2 uint32, R3 uint32, R4 uint32, R5 uint32, R6 uint32, R7 uint32, R8 uint32,
      R9 uint32, R10 varchar(1), DOCMETHOD uint32, STATE uint32, EASTING_MAX x_coordinate, EASTING_MIN real32, NORTHING_MIN y_coordinate, NORTHING_MAX real64, R13 varchar(1)
    -> FeatureMerger_4 [REQUESTOR]
FeatureMerger_4
    ATTR_ACCUM_MODE = Merge Supplier
    ATTR_CONFLICT_RES_LOOKUP = REQUESTOR_IF_CONFLICT
    IGNORE_NULLS = No
    JOIN_KEYS = 1 1 AUTO
    MERGE_TYPE = Attributes and Geometry
    PRESERVE_FEATURE_ORDER_LOOKUP = PER_OUTPUT_PORT
    PROCESS_DUPS = NO
    REJECT_NULL_MISSING_KEYS = No
    SUPPLIERS_FIRST = No
    ATTR_CONFLICT_RES = Use Requestor
    MERGED -> project_information (writer OGCGEOPACKAGE_1)
project_information (writer OGCGEOPACKAGE_1)
    attributes: EASTING_MAX double, NORTHING_MIN double, NORTHING_MAX double, EASTING_MIN float, PROJECT int, R1 int, R2 int, R3 int, R4 int, R5 int, R6 int, R7 int, R8 int, R9 int, DOCMETHOD int, STATE int, OFFICALDESIGNATION text, PROJECTNAME text, CLIENT text, PREMISES text, PARISH text, MONUMENT text, MUNICIPALITY text, COUNTY text, PROVINCE text, BASEMAP text, PROJECTMANAGER text, PARTICIPANTS text, TYPEOFPROJECT text, STARTOFPROJECT text,
      ENDOFPROJECT text, MANHOURS text, MACHINEHOURS text, AREAOFINVEST text, COORDINATESYST text, HEIGHTSYST text, MASL text, R10 text, R13 text

Bookmark: gpkext_relations
Creator_2
    GEOMTYPE = Geometry Object
    NUM = 1
    CREATED -> AttributeManager_4
AttributeManager_4
    ATTR_TABLE:
      REMOVE _creation_instance
      SET_TO id = 1
      SET_TO base_table_name = objects
      SET_TO base_primary_column = OBJECTNO_SUBOBJECT_IDX
      SET_TO mapping_table_name = object_relations
      SET_TO related_primary_column = OBJECTNO_SUBOBJECT_IDX
      SET_TO related_table_name = objects
      SET_TO relation_name = obj2obj
    USER_EXPOSED_ATTRIBUTES = _creation_instance
    -> gpkgext_relations (writer SQLITE3_2)
gpkgext_relations (writer SQLITE3_2)
    attributes: id integer, base_table_name text, base_primary_column text, related_table_name text, related_primary_column text, relation_name text, mapping_table_name text,Unique

Bookmark: gpkg_extension
Creator
    GEOMTYPE = Geometry Object
    NUM = 1
    CREATED -> AttributeManager
    CREATED -> AttributeManager_2
AttributeManager
    ATTR_TABLE:
      REMOVE _creation_instance
      SET_TO column_name
      SET_TO definition = http://www.geopackage.org/18-000.html
      SET_TO extension_name = related_tables
      SET_TO scope = read-write
      SET_TO table_name = object_relations
    -> gpkg_extensions (writer SQLITE3_2)
AttributeManager_2
    ATTR_TABLE:
      REMOVE _creation_instance
      SET_TO column_name
      SET_TO definition = http://www.geopackage.org/18-000.html
      SET_TO extension_name = related_tables
      SET_TO scope = read-write
      SET_TO table_name = gpkgext_relations
    -> gpkg_extensions (writer SQLITE3_2)
gpkg_extensions (writer SQLITE3_2)
    attributes: table_name text,Unique, column_name text,Unique, extension_name text,Unique, definition text, scope text

Bookmark: object_relations
Note: CSV: RELATIONS
CSV (reader CSV2_1)
    attributes: PROJECT uint32, CATEGORY varchar(12), OBJECTNO uint32, SUBOBJECT uint32, RTYPE uint32, COBJECTNO uint32, CSUBOBJECT uint32
    -> Counter
Counter
    CNT_ATTR = _count
    DOMAIN = counter
    SCOPE = Global
    START = 0
    -> FeatureMerger [REQUESTOR]
RTYPE (reader XLSXR_1)
    attributes: value number(1,0), base_text char(12), related_text char(12)
    -> FeatureMerger [SUPPLIER]
FeatureMerger
    ATTR_ACCUM_MODE = Merge Supplier
    ATTR_CONFLICT_RES_LOOKUP = REQUESTOR_IF_CONFLICT
    IGNORE_NULLS = No
    JOIN_KEYS = @Value(RTYPE) @Value(value) AUTO
    MERGE_TYPE = Attributes Only
    PROCESS_DUPS = NO
    REJECT_NULL_MISSING_KEYS = No
    SUPPLIERS_FIRST = No
    ATTR_CONFLICT_RES = Use Requestor
    MERGED -> AttributeManager_3
AttributeManager_3
    ATTR_TABLE:
      RENAME_SET_VALUE _count > id
      SET_TO base_id = @Value(OBJECTNO)_@Value(SUBOBJECT)_0
      SET_TO related_id = @Value(COBJECTNO)_@Value(CSUBOBJECT)_0
    USER_EXPOSED_ATTRIBUTES = PROJECT,CATEGORY,OBJECTNO,SUBOBJECT,RTYPE,COBJECTNO,CSUBOBJECT,_count
    -> object_relations (writer SQLITE3_2)
object_relations (writer SQLITE3_2)
    attributes: id integer, base_id text, related_id text, base_text text, related_text text

FME custom transformer rtfAll2

Parameters:
- NOTES = @Value(NOTES)
- OBJECTID = @Value(OBJECTID)
- INTERPRETATIONS = @Value(INTERPRETATIONS)
- OBSERVATIONS = @Value(OBSERVATIONS)

AttributeKeeper_Input (input)
    -> AttributeKeeper
AttributeKeeper
    CREATE_BULK_MODE_FEATURES = NO
    KEEP_ATTRS = NOTES,OBSERVATIONS,INTERPRETATIONS,OBJECTID
    -> RTFdecode2_3 [AttributeManager_2_Input]
    -> RTFdecode2 [AttributeManager_2_Input]
    -> RTFdecode2_2 [AttributeManager_2_Input]
    -> FeatureMerger [REQUESTOR]
RTFdecode2
    INDATA = @Value(OBSERVATIONS)
    OBJECTID = @Value(OBJECTID)
    -> AttributeManager
Note: OBSERVATIO_NS
AttributeManager
    ATTR_TABLE:
      RENAME_SET_VALUE utdata > utdata_obs (varchar(200))
      SET_TO OBSERVATIONS (buffer)
    -> FeatureMerger [SUPPLIER]
RTFdecode2_2
    INDATA = @Value(NOTES)
    OBJECTID = @Value(OBJECTID)
    -> AttributeManager_3
Note: NOTES
AttributeManager_3
    ATTR_TABLE = RENAME_SET_VALUE utdata > utdata_notes (varchar(200))
    -> FeatureMerger [SUPPLIER]
RTFdecode2_3
    INDATA = @Value(INTERPRETATIONS)
    OBJECTID = @Value(OBJECTID)
    -> AttributeManager_2
Note: INTERPRETATIONS
AttributeManager_2
    ATTR_TABLE = RENAME_SET_VALUE utdata > utdata_int (varchar(200))
    -> FeatureMerger [SUPPLIER]
FeatureMerger
    ATTR_ACCUM_MODE = Merge Supplier
    ATTR_CONFLICT_RES_LOOKUP = SUPPLIER_IF_CONFLICT
    CLEANING_TOLERANCE_LOOKUP = AUTO
    CONNECT_Z_MODE_LOOKUP = FIRST_WINS
    GEOM_TYPE_VAL = POLYGONS
    IGNORE_NULLS = No
    JOIN_KEYS = @Value(OBJECTID) @Value(OBJECTID) AUTO
    MERGE_TYPE = Attributes Only
    PROCESS_DUPS = YES
    REJECT_NULL_MISSING_KEYS = No
    SUPPLIERS_FIRST = No
    ATTR_CONFLICT_RES = Use Supplier
    CLEANING_TOLERANCE = Automatic
    CONNECT_Z_MODE = First Wins
    GEOM_TYPE = Build Polygons
    MERGED -> AttributeManager_4
AttributeManager_4
    ATTR_TABLE:
      SET_TO NOTES (buffer) = @Value(utdata_notes)
      SET_TO INTERPRETATIONS (buffer) = @Value(utdata_int)
      SET_TO OBSERVATIONS (buffer) = @Value(utdata_obs)
    -> AttributeManager_5
AttributeManager_5
    ATTR_TABLE:
      REMOVE utdata_obs (varchar(200))
      REMOVE indata (varchar(200))
      REMOVE utdata_notes (varchar(200))
      REMOVE utdata_int (varchar(200))
    -> AttributeManager_5_Output (output)
AttributeManager_5_Output (output)

FME custom transformer RTFdecode2

Parameters:
- INDATA = @Value(indata)   # indata
- OBJECTID = @Value(OBJECTID)

AttributeManager_2_Input (input)
    -> AttributeManager
AttributeManager
    USER_EXPOSED_ATTRIBUTES = INTERPRETATIONS
    -> AttributeManager_2
Note: å ä ö igen
AttributeManager_10
    ATTR_TABLE = SET_TO indata10 (varchar(200)) = @ReplaceString(@ReplaceString(@ReplaceString(@ReplaceString(@ReplaceString(@ReplaceString(@ReplaceString(@Value(indata9),\\'f6,ö,caseSensitive=TRUE),\\'e4,ä, caseSensitive=TRUE),\\'e5,å, ,caseSensitive=TRUE),\\'d6,Ö, ,caseSensitive=TRUE),\xf6,ö, ,caseSensitive=TRUE),\xf5,å, ,caseSensitive=TRUE),\xd6,Ö, ,caseSensitive=TRUE)
    -> AttributeManager_12
AttributeManager_14
    ATTR_TABLE = SET_TO indata13 (varchar(200)) = @ReplaceString(@Value(indata12),{\tf1\\ansi\\ansicpg1252\\deff0{\\fonttbl{\\fnil\\fcharset0 MS Sans Serif;}{\\froman\\fcharset0 Times New Roman;}{\\f2\\fnil MS Sans Serif;}}\\viewkind4\\uc1\\pard\\sb100\\sa100\\lang1053\\fs16,,caseSensitive=TRUE)
    -> AttributeManager_15
AttributeManager_15
    ATTR_TABLE = SET_TO indata14 (varchar(200)) = @ReplaceString(@Value(indata13),{\tf1\\ansi\\deff0{\\fonttbl{\\fnil MS Sans Serif;}}\\viewkind4\\uc1\\pard\\lang1053\\fs16,,caseSensitive=TRUE)
    -> AttributeManager_17
AttributeManager_17
    ATTR_TABLE = SET_TO indata15 (varchar(200)) = @ReplaceString(@Value(indata14),\\par\\par}\x00,,caseSensitive=TRUE)
    -> AttributeManager_18
AttributeManager_18
    ATTR_TABLE = SET_TO indata16 (varchar(200)) = @ReplaceString(@Value(indata15),\\par}\x00,,caseSensitive=TRUE)
    -> AttributeManager_16
Note: set utdata
AttributeManager_16
    ATTR_TABLE:
      RENAME_SET_VALUE indata14 (varchar(200))
      SET_TO utdata (varchar(200)) = @Value(indata16)
    -> Output (output)
Output (output)

Bookmark: åäö
AttributeManager_2
    ATTR_TABLE = SET_TO indata (varchar(200)) = @ReplaceString(@ReplaceString(@ReplaceString(@Value(indata),\xe6,ö,caseSensitive=TRUE),\xe4,ä, caseSensitive=TRUE),\xe5,å, ,caseSensitive=TRUE)
    -> AttributeManager_3

Bookmark: diverse fonformateringar
Note: ansicpg1252\\deff0
AttributeManager_3
    ATTR_TABLE:
      RENAME_SET_VALUE indata (varchar(200))
      RENAME_SET_VALUE indata2 (varchar(200)) = @ReplaceString(@Value(indata),"{\\rtf1\\ansi\\ansicpg1252\\deff0{\\fonttbl{\\f0\\fnil\\fcharset0 MS Sans Serif;}{\\f1\\fnil MS Sans Serif;}}\r\n\\viewkind4\\uc1\\pard\\lang1053\\f0\\fs16"
        ,,caseSensitive=TRUE)
    USER_EXPOSED_ATTRIBUTES = obs,obs2,OBSERVATIONS,inda
    -> AttributeManager_4
Note: deff0
AttributeManager_4
    ATTR_TABLE = SET_TO indata3 (varchar(200)) = @ReplaceString(@Value(indata2),"{\\rtf1\\ansi\\deff0{\\fonttbl{\\f0\\fnil\\fcharset0 MS Sans Serif;}{\\f1\\fnil MS Sans Serif;}}\r\n\\viewkind4\\uc1\\pard\\lang1053\\f0\\fs16",,caseSensitive=TRUE)
    USER_EXPOSED_ATTRIBUTES = obs
    -> AttributeManager_5
AttributeManager_5
    ATTR_TABLE = SET_TO indata4 (varchar(200)) = @ReplaceString(@Value(indata3),"{\\rtf1\\ansi\\ansicpg1252\\deff0{\\fonttbl{\\f0\\fnil\\fcharset0 MS Sans Serif;}{\\f1\\fnil MS Sans Serif;}}\r\n\\viewkind4\\uc1\\pard\\lang1053\\f0\\fs16",,caseSensitive=TRUE)
    -> AttributeManager_6
AttributeManager_6
    ATTR_TABLE = SET_TO indata5 (varchar(200)) = @ReplaceString(@Value(indata4),"{\\rtf1\\ansi\\ansicpg1252\\deff0{\\fonttbl{\\f0\\fnil MS Sans Serif;}{\\f1\\fnil\\fcharset0 MS Sans Serif;}}\r\n\\viewkind4\\uc1\\pard\\lang1053\\f0\\fs16",,caseSensitive=TRUE)
    -> AttributeManager_7
AttributeManager_7
    ATTR_TABLE = SET_TO indata6 (varchar(200)) = @ReplaceString(@Value(indata5),"{\\rtf1\\ansi\\deff0{\\fonttbl{\\f0\\fnil MS Sans Serif;}{\\f1\\fnil\\fcharset0 MS Sans Serif;}}\r\n\\viewkind4\\uc1\\pard\\lang1053\\f0\\fs16",,caseSensitive=TRUE)
    -> AttributeManager_8

Bookmark: start b'' b'
AttributeManager_8
    ATTR_TABLE = SET_TO indata7 (varchar(200)) = @ReplaceString(@Value(indata6),b'',,caseSensitive=TRUE)
    -> AttributeManager_9
AttributeManager_9
    ATTR_TABLE = SET_TO indata8 (varchar(200)) = @ReplaceString(@Value(indata7),"b\"",,caseSensitive=TRUE)
    -> AttributeManager_11
AttributeManager_11
    ATTR_TABLE = SET_TO indata9 (varchar(200)) = @ReplaceString(@Value(indata8),b',,caseSensitive=TRUE)
    -> AttributeManager_10

Bookmark: diverse formateringar 2
Note: \\f
AttributeManager_12
    ATTR_TABLE = SET_TO indata11 (varchar(200)) = @ReplaceString(@ReplaceString(@ReplaceString(@Value(indata10),\\f1,,caseSensitive=TRUE),\r,,caseSensitive=TRUE),\n,,caseSensitive=TRUE)
    -> AttributeManager_13
AttributeManager_13
    ATTR_TABLE = SET_TO indata12 (varchar(200)) = @ReplaceString(@ReplaceString(@ReplaceString(@Value(indata11),\\par\r\n}\r\n\x00,,caseSensitive=TRUE),\\f0,,caseSensitive=TRUE),\\f0\\par}\x00,,caseSensitive=TRUE)
    -> AttributeManager_14
