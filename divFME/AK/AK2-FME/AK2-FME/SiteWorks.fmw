FME workspace SiteWorks.fmw

Parameters:
- SourceDataset_ODBC2 = SiteWorks   # Source ODBC 3.x Dataset
- DestDataset_FILEGDB = $(FME_MF_DIR)AK\Siteworks.gdb   # Destination Geodatabase

Readers:
- ODBC2_1: ODBC2 from $(SourceDataset_ODBC2)

Writers:
- FILEGDB_1: FILEGDB to $(DestDataset_FILEGDB) in EPSG:3006

OBJDATA (reader ODBC2_1)
    attributes: SEQNO smallint, X double, Y double, Z double, OBJECTID integer
    -> Sorter
    -> 3DPointAdder
Sorter [off]
    SORT_PARM = OBJECTID NUMERIC ASCENDING SEQNO NUMERIC ASCENDING
    SORTED -> 3DPointAdder
3DPointAdder
    XVALATTR = @Value(X)
    ZVALATTR = @Value(Z)
    YVALATTR = @Value(Y)
    -> PointConnector
PointConnector
    BREAKATTR = OBJECTID
    POLYGON -> Joiner
    LINE -> Joiner
    POINT -> Joiner_3
Joiner_3
    ODBC2_PASSWORD = masterkey
    TABLE = OBJECTS
    MATCH_MULTIPLE_DISPLAY = Create a feature for each match
    MATCH_RULE_DISPLAY = Match All (1:M)
    ADDED_FIELDS = PROJECT OBJECTNO SUBOBJECT TYPENO
    PREFETCH_EXHAUSTIVE = Yes
    DATASET = SiteWorks
    JOIN_KEYS = OBJECTID OBJECTID
    CACHE_SIZE = 5000
    ODBC2_USER_NAME = sysdba
    FORMAT = ODBC2
    JOINED -> Joiner_4
Joiner_4
    ODBC2_PASSWORD = masterkey
    TABLE = OBJTYP
    MATCH_MULTIPLE_DISPLAY = Create a feature for each match
    MATCH_RULE_DISPLAY = Match All (1:M)
    ADDED_FIELDS = CATEGORY CLASS TYPENAME ELEMENT_TYPE CLOSED
    PREFETCH_EXHAUSTIVE = Yes
    DATASET = SiteWorks
    JOIN_KEYS = TYPENO TYPENR
    CACHE_SIZE = 5000
    ODBC2_USER_NAME = sysdba
    FORMAT = ODBC2
    JOINED -> points (writer FILEGDB_1)
    JOINED -> BoundingBoxAccumulator
points (writer FILEGDB_1)
    attributes: PROJECT text(200), CATEGORY text(32), TYPENAME text(30), OBJECTNO int, SUBOBJECT int, CLASS text(32)
Joiner
    ODBC2_PASSWORD = masterkey
    TABLE = OBJECTS
    MATCH_MULTIPLE_DISPLAY = Create a feature for each match
    MATCH_RULE_DISPLAY = Match All (1:M)
    ADDED_FIELDS = PROJECT OBJECTNO SUBOBJECT TYPENO
    PREFETCH_EXHAUSTIVE = Yes
    DATASET = SiteWorks
    JOIN_KEYS = OBJECTID OBJECTID
    CACHE_SIZE = 5000
    ODBC2_USER_NAME = sysdba
    FORMAT = ODBC2
    JOINED -> Joiner_2
Joiner_2
    ODBC2_PASSWORD = masterkey
    TABLE = OBJTYP
    MATCH_MULTIPLE_DISPLAY = Create a feature for each match
    MATCH_RULE_DISPLAY = Match All (1:M)
    ADDED_FIELDS = CATEGORY CLASS TYPENAME ELEMENT_TYPE CLOSED
    PREFETCH_EXHAUSTIVE = Yes
    DATASET = SiteWorks
    JOIN_KEYS = TYPENO TYPENR
    CACHE_SIZE = 5000
    ODBC2_USER_NAME = sysdba
    FORMAT = ODBC2
    JOINED -> Tester
    JOINED -> BoundingBoxAccumulator
BoundingBoxAccumulator
    GROUP_BY = PROJECT
    TOPFER_INDEX = No
    BOUNDING_BOX -> Joiner_5
    BOUNDING_BOX -> FeatureMerger [input 1]
Joiner_5
    ODBC2_PASSWORD = masterkey
    TABLE = PROJECT
    MATCH_MULTIPLE_DISPLAY = Create a feature for each match
    MATCH_RULE_DISPLAY = Match All (1:M)
    ADDED_FIELDS = PROJECT OFFICALDESIGNATION PROJECTNAME CLIENT PREMISES PARISH MONUMENT MUNICIPALITY COUNTY PROVINCE BASEMAP PROJECTMANAGER PARTICIPANTS TYPEOFPROJECT STARTOFPROJECT ENDOFPROJECT MANHOURS MACHINEHOURS AREAOFINVEST COORDINATESYST HEIGHTSYST MASL R1 R2 R3 R4 R5 R6 R7 R8 R9 R10 DOCMETHOD STATE EASTING_MAX EASTING_MIN NORTHING_MIN NORTHING_MAX R13
    PREFETCH_EXHAUSTIVE = Yes
    DATASET = SiteWorks
    JOIN_KEYS = PROJECT PROJECT
    CACHE_SIZE = 5000
    ODBC2_USER_NAME = sysdba
    FORMAT = ODBC2
    JOINED -> FeatureMerger [input 2]
FeatureMerger
    PROCESS_DUPS = No
    MERGE_TYPE = Attributes Only
    JOIN_KEYS = @Value(PROJECT) @Value(PROJECT)
    SUPPLIER_PREFIX_DUMMY = YES
    MERGED -> projects (writer FILEGDB_1)
projects (writer FILEGDB_1)
    attributes: PROJECT text(200), OFFICALDESIGNATION text(12), PROJECTNAME text(64), CLIENT text(64), PREMISES text(64), PARISH text(32), MONUMENT text(6), MUNICIPALITY text(32), COUNTY text(32), PROVINCE text(32), PROJECTMANAGER text(32), PARTICIPANTS text(200), TYPEOFPROJECT text(32), STARTOFPROJECT text(32), ENDOFPROJECT text(32), MANHOURS int, MACHINEHOURS int, AREAOFINVEST int, COORDINATESYST text(16), HEIGHTSYST text(16), MASL double, DOCMETHOD int
Tester
    TEST_MODE = Automatic
    TEST_DESCRIPTION = ""
    BOOL_OP = OR
    TEST_CLAUSE = TEST @Value(ELEMENT_TYPE) = 4
    PASSED -> GeometryCoercer
    FAILED -> GeometryFilter
GeometryCoercer
    KIND = fme_line
    COERCED -> lines (writer FILEGDB_1)
lines (writer FILEGDB_1)
    attributes: PROJECT text(200), CATEGORY text(32), TYPENAME text(30), OBJECTNO int, SUBOBJECT int, CLASS text(32)
GeometryFilter
    BREAK_AGG = No
    LINE -> LineCloser
    AREA -> polygons (writer FILEGDB_1)
LineCloser
    AREA -> GeometryCoercer_2
GeometryCoercer_2
    CHECKZ = No
    KIND = fme_polygon
    COERCED -> polygons (writer FILEGDB_1)
polygons (writer FILEGDB_1)
    attributes: PROJECT text(200), CATEGORY text(32), TYPENAME text(30), OBJECTNO int, SUBOBJECT int, CLASS text(32)

FME custom transformer LoopFilter
Tests whether a line is a loop, i.e. whether its end matches the beginning.
The transformers outputs loops through PASSED port, and non-loops through FAILED port.
An isLoop attribute is added to each feature. 1 means the feature is loop, and zero means it is not.
Copyright (c) 2012 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

LINE (input)
    -> LineFilter
Note: LoopFilter / Dmitri Bagh / July 11, 2005
LineFilter: GeometryFilter
    LINE -> LoopTester
    POINT -> NON-LINEAR (output)
    ARC -> NON-LINEAR (output)
    AREA -> NON-LINEAR (output)
    ELLIPSE -> NON-LINEAR (output)
    TEXT -> NON-LINEAR (output)
    NULL -> NON-LINEAR (output)
Note: LoopTester [ExpressionEvaluator] / _isLoop = (@Coordinate(x,0)-@Coordinate(x,-1))||(@Coordinate(y,0)-@Coordinate(y,-1))
Note: Evaluates to 0 if feature is loop, and 1, if it is not.
LoopTester: ExpressionEvaluator
    VAL_ATTR = _isLoop
    EXPRESSION = (@Coordinate(x,0)-@Coordinate(x,-1))||(@Coordinate(y,0)-@Coordinate(y,-1))
    -> TESTER
Note: TESTER [Tester] / Test Description: / TEST &_isLoop = 0 / Condition: OR / Composite Test Expression:
TESTER: Tester
    TEST_MODE = Automatic
    BOOL_OP = OR
    TEST_LIST = &_isLoop,=,0
    TEST_CLAUSE = TEST &_isLoop = 0
    PASSED -> PASSED (output)
    FAILED -> FAILED (output)
PASSED (output)
FAILED (output)
NON-LINEAR (output)
