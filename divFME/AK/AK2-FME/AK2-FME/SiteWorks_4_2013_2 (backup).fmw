FME workspace SiteWorks_4_2013_2 (backup).fmw
Startup Python:
      import fmeobjects
      from _winreg import *
      def editdb():
          try:
              dbn=FME_MacroValues['dbname']
              keyval=r"SOFTWARE\ODBC\ODBC.INI\SiteWorks"
              Registrykey= OpenKey(HKEY_CURRENT_USER, keyval, 0,KEY_WRITE)
              SetValueEx(Registrykey,"Dbname",0,REG_SZ,"localhost:"+dbn)
              CloseKey(Registrykey)
              return True
          except WindowsError:
              return False

      editdb()

Parameters:
- DestDataset_FILEGDB = c:\Siteworks.gdb   # Destination Geodatabase
- SourceDataset_ODBC2_3 = SiteWorks   # Source ODBC 3.x Dataset
- DestDataset_SHAPE = $(FME_MF_DIR)AK   # Destination Esri Shape Directory
- dbname = c:\projekt\siteworks_db\siteworks.gdb
- DestDataset_FILEGDB_9 = C:\Siteworks.gdb   # Destination Geodatabase
- DestDataset_FILEGDB_7 = projekt_yta   # Destination Geodatabase
- DestDataset_FILEGDB_11 = Siteworks   # Destination Geodatabase
- DestDataset_XLSXW = P:\RAa_arkeologisk_dokumentation\Steg3\AK\projektlista_FME.xlsx   # Destination Microsoft Excel File
- DestDataset_FILEGDB_8 = Siteworks   # Destination Geodatabase
- DestDataset_FILEGDB_10 = Siteworks   # Destination Geodatabase

Readers:
- ODBC2_1: ODBC2 from $(SourceDataset_ODBC2_3)

Writers:
- FILEGDB_1: FILEGDB to $(DestDataset_FILEGDB) in EPSG:3006
- SHAPE_1: SHAPE to $(DestDataset_SHAPE)
- FILEGDB_2: FILEGDB to $(DestDataset_FILEGDB_9)
- FILEGDB_3: FILEGDB to $(DestDataset_FILEGDB_7)
- FILEGDB_4: FILEGDB to $(DestDataset_FILEGDB_11)
- XLSXW_1: XLSXW to $(DestDataset_XLSXW)
- FILEGDB_5: FILEGDB to $(DestDataset_FILEGDB_8)
- FILEGDB_6: FILEGDB to $(DestDataset_FILEGDB_10)

OBJDATA (reader ODBC2_1)
    attributes: SEQNO smallint, X double, Y double, Z double, OBJECTID integer
    -> Tester_9
Tester_9
    TEST_MODE = Automatic
    TEST_DESCRIPTION = ""
    BOOL_OP = AND
    TEST_CLAUSE:
      TEST X NOT_ATTRIBUTE_IS_NULL <Unused>
      TEST Y NOT_ATTRIBUTE_IS_NULL <Unused>
      TEST @Value(X) NOT_= 0
      TEST @Value(Y) NOT_= 0
    PASSED -> Tester_4
Tester_4
    TEST_MODE = Automatic
    TEST_DESCRIPTION = ""
    BOOL_OP = OR
    TEST_CLAUSE = TEST Z ATTRIBUTE_IS_NULL <Unused>
    PASSED -> AttributeCreator
    FAILED -> 3DPointAdder
AttributeCreator
    ATTR_LIST = Z,0
    -> 3DPointAdder
3DPointAdder
    XVALATTR = @Value(X)
    ZVALATTR = @Value(Z)
    YVALATTR = @Value(Y)
    -> PointConnector
PointConnector
    BREAKATTR = OBJECTID
    POINT -> AttributeKeeper
    POLYGON -> AttributeKeeper_2
    LINE -> AttributeKeeper_2
AttributeKeeper
    KEEP_ATTRS = OBJECTID
    -> Joiner_3
Joiner_3
    ODBC2_PASSWORD = masterkey
    TABLE = OBJECTS
    MATCH_RULE_DISPLAY = Match First (1:0..1+)
    ADDED_FIELDS = PROJECT OBJECTNO SUBOBJECT TYPENO
    PREFETCH_EXHAUSTIVE = Yes
    DATASET = SiteWorks
    JOIN_KEYS = OBJECTID OBJECTID
    CACHE_SIZE = 5000
    ODBC2_USER_NAME = sysdba
    FORMAT = ODBC2
    JOINED -> Joiner_4
Joiner_4
    ODBC2_PASSWORD = masterkey
    TABLE = OBJTYP
    MATCH_RULE_DISPLAY = Match First (1:0..1+)
    ADDED_FIELDS = CATEGORY CLASS TYPENAME ELEMENT_TYPE CLOSED
    PREFETCH_EXHAUSTIVE = Yes
    DATASET = SiteWorks
    JOIN_KEYS = TYPENO TYPENR
    CACHE_SIZE = 5000
    ODBC2_USER_NAME = sysdba
    FORMAT = ODBC2
    JOINED -> DuplicateRemover_2
DuplicateRemover_2
    KEYATTR = PROJECT OBJECTNO SUBOBJECT CATEGORY
    UNIQUE -> Matcher_4
Matcher_4
    MATCHATTRS = PROJECT OBJECTNO SUBOBJECT CATEGORY
    BLANK_AND_MISSING_DIFFER_DISP = As Missing Attribute
    MATCH = NONE
    MATCH_STRATEGY = Match Selected Attributes
    LENIENT_MATCH = No
    CNT_ATTR = _match_id
    SINGLE_MATCHED -> Joiner_6
    NOT_MATCHED -> Joiner_6
AttributeKeeper_2
    KEEP_ATTRS = OBJECTID
    -> Joiner
Joiner
    ODBC2_PASSWORD = masterkey
    TABLE = OBJECTS
    MATCH_RULE_DISPLAY = Match First (1:0..1+)
    ADDED_FIELDS = PROJECT CATEGORY OBJECTNO SUBOBJECT TYPENO DESCRIPTION SUBCLASS DEFINITION INTERPRETATIONS X_AVG Y_AVG Z_AVG OBJLENGTH WIDTH NUMBEROF WEIGHT BELONGSTO BELONGSTOSUB BELONGSTOTYPE CONTEXT CONTEXTOBJECT CONTEXTSUBOBJECT CONTEXTTYPE INCLINATION DATEOFRECORDING MPRECISION SIGN DATING DATINGMETHOD NONMEASUREDLOCATION MEASUREMENTFILE STRUCKOFF CONSTRUCTION SUBCONSTRUCTION ORIENTATION FORM COURNERS HEIGHT RIM BOTTOMRIM BOTTOM SECTION CONDITION SPLITTING TOOLTRACES ASSEMBLY MATERIAL GRANULARITY SURFACE JOINTINGMATERIAL SORTING STRUCTURE CONTENTS CONSISTENCE PACKING COLOUR COMPOSITION JOINTING CHALK COAL PEBBELS BRICKFRAG BRICK WOOD CLAY BURNT_CLAY DAUB GRAVEL SOOT ASHES ANIMALBONES FISHBONES MACHINE SHOVEL HOETABLE TROWEL SIEVE PREPARATION CONTAMINATION DROUGHT RAIN FROST WATERSIEVE RECORDEDBY VERIFIED OBSERVATIONS CONTACT_BELOW SIDE LIMITS MAXHEIGHT DETAILS TAQ TPQ STRATATOP STRATABOTTOM SAND LIME PREV_FUNCTION DATEEDITED BLAZINGCOLOR FILLING TIERS TIER_DEPTH OBJECTID BELONGSTOID CONST_PHASE DEST_PHASE AREA SILT ORGANIC_MATTER IDX NOTES DIAMETER ROCKS HUMUS BURNT_BONE UNBURNT_BONE FIRE_CRACKED_ROCK BURNT_STONE PART DATING_MARGINOFERROR BOULDERS CONTACT_ABOVE
    PREFETCH_EXHAUSTIVE = Yes
    DATASET = SiteWorks
    JOIN_KEYS = OBJECTID OBJECTID
    CACHE_SIZE = 5000
    ODBC2_USER_NAME = sysdba
    FORMAT = ODBC2
    JOINED -> Joiner_2
Joiner_2
    ODBC2_PASSWORD = masterkey
    TABLE = OBJTYP
    MATCH_RULE_DISPLAY = Match First (1:0..1+)
    ADDED_FIELDS = CATEGORYCODE CATEGORY CLASS TYPENAME ELEMENT_TYPE CLOSED
    PREFETCH_EXHAUSTIVE = Yes
    DATASET = SiteWorks
    JOIN_KEYS = TYPENO TYPENR
    CACHE_SIZE = 5000
    ODBC2_USER_NAME = sysdba
    FORMAT = ODBC2
    JOINED -> Tester
Tester
    TEST_MODE = Automatic
    TEST_DESCRIPTION = ""
    BOOL_OP = OR
    TEST_CLAUSE:
      TEST @Value(ELEMENT_TYPE) = 4
      TEST @Value(ELEMENT_TYPE) = 3
    PASSED -> GeometryCoercer
    FAILED -> GeometryFilter
GeometryCoercer
    KIND = fme_line
    COERCED -> Matcher_3
Matcher_3
    MATCHATTRS = PROJECT CATEGORY OBJECTNO SUBOBJECT IDX
    BLANK_AND_MISSING_DIFFER_DISP = As Missing Attribute
    MATCH = NONE
    MATCH_STRATEGY = Match Selected Attributes
    LENIENT_MATCH = No
    CNT_ATTR = _match_id
    SINGLE_MATCHED -> Joiner_6
    NOT_MATCHED -> Joiner_6
GeometryFilter
    BREAK_AGG = No
    LINE -> LineCloser
    ARC -> AttributeFilter
LineCloser
    AREA -> GeometryCoercer_2
GeometryCoercer_2
    CHECKZ = No
    KIND = fme_polygon
    COERCED -> AttributeFilter
AttributeFilter
    ATTR_NAME = CATEGORYCODE
    ATTR_VALUES = <BLANK>,<UNFILTERED>,-K,-I
    -K -> DuplicateRemover
    -K -> Matcher
    <BLANK> -> Matcher_2
    <UNFILTERED> -> Matcher_2
    -I -> Matcher_5
Matcher_2
    MATCHATTRS = PROJECT CATEGORY OBJECTNO SUBOBJECT IDX
    BLANK_AND_MISSING_DIFFER_DISP = As Missing Attribute
    MATCH = NONE
    MATCH_STRATEGY = Match Selected Attributes
    LENIENT_MATCH = No
    CNT_ATTR = _match_id
    SINGLE_MATCHED -> Joiner_6
    NOT_MATCHED -> Joiner_6
Matcher
    MATCHATTRS = PROJECT CATEGORY OBJECTNO SUBOBJECT IDX
    BLANK_AND_MISSING_DIFFER_DISP = As Missing Attribute
    MATCH = NONE
    MATCH_STRATEGY = Match Selected Attributes
    LENIENT_MATCH = No
    CNT_ATTR = _match_id
    SINGLE_MATCHED -> Joiner_6
    NOT_MATCHED -> Joiner_6
DuplicateRemover [off]
    KEYATTR = PROJECT CATEGORY OBJECTNO SUBOBJECT IDX
    UNIQUE -> Joiner_6
Matcher_5
    MATCHATTRS = PROJECT CATEGORY OBJECTNO SUBOBJECT IDX
    BLANK_AND_MISSING_DIFFER_DISP = As Missing Attribute
    MATCH = 2D
    MATCH_STRATEGY = Match Selected Attributes
    LENIENT_MATCH = No
    CNT_ATTR = _match_id
    SINGLE_MATCHED -> Joiner_6
    NOT_MATCHED -> Joiner_6
Joiner_6
    ODBC2_PASSWORD = masterkey
    TABLE = PROJECT
    MATCH_RULE_DISPLAY = Match First (1:0..1+)
    ADDED_FIELDS = COORDINATESYST
    PREFETCH_EXHAUSTIVE = Yes
    DATASET = SiteWorks
    JOIN_KEYS = PROJECT PROJECT
    CACHE_SIZE = 50000
    ODBC2_USER_NAME = sysdba
    FORMAT = ODBC2
    JOINED -> BoundsExtractor
BoundsExtractor
    YMIN = _ymin
    ZMIN = _zmin
    XMIN = _xmin
    XMAX = _xmax
    ZMAX = _zmax
    YMAX = _ymax
    -> Tester_7
Tester_7
    TEST_MODE = Automatic
    TEST_DESCRIPTION = ""
    BOOL_OP = OR
    TEST_CLAUSE = TEST @Value(_xmax) > 1000000
    PASSED -> Reproj_RT90
    FAILED -> Tester_8
Reproj_RT90: Reprojector
    DEST = EPSG:3006
    RASTER_CELL_SIZE = Preserve Cells
    STROKE_ARCS = Yes
    SOURCE = EPSG:2400
    INTERPOLATION_TYPE_NAME = Nearest Neighbor
    REPROJECTED -> GeometryFilter_2
    REPROJECTED -> BoundingBoxAccumulator_2
Tester_8
    TEST_MODE = Automatic
    TEST_DESCRIPTION = ""
    BOOL_OP = AND
    TEST_CLAUSE = TEST @Value(_xmax) < 300000
    FAILED -> GeometryFilter_2
    FAILED -> BoundingBoxAccumulator_2
    PASSED -> Tester_2
Tester_2
    TEST_MODE = Automatic
    TEST_DESCRIPTION = ""
    BOOL_OP = OR
    TEST_CLAUSE = TEST @Value(COORDINATESYST) CONTAINS SW
    FAILED -> Reproj_ST74
    PASSED -> Reprojector_SW18
Reprojector_SW18
    DEST = EPSG:3006
    RASTER_CELL_SIZE = Preserve Cells
    STROKE_ARCS = Yes
    SOURCE = SWEREF-99-18-00
    INTERPOLATION_TYPE_NAME = Nearest Neighbor
    REPROJECTED -> GeometryFilter_2
    REPROJECTED -> BoundingBoxAccumulator_2
Reproj_ST74: Reprojector
    DEST = EPSG:3006
    RASTER_CELL_SIZE = Preserve Cells
    STROKE_ARCS = Yes
    SOURCE = EPSG:3152
    INTERPOLATION_TYPE_NAME = Nearest Neighbor
    REPROJECTED -> GeometryFilter_2
    REPROJECTED -> BoundingBoxAccumulator_2
BoundingBoxAccumulator_2
    GROUP_BY = PROJECT
    TOPFER_INDEX = No
    BOUNDING_BOX -> Joiner_5
Joiner_5
    ODBC2_PASSWORD = masterkey
    TABLE = PROJECT
    MATCH_MULTIPLE_DISPLAY = Create a feature for each match
    MATCH_RULE_DISPLAY = Match All (1:M)
    ADDED_FIELDS = PROJECT OFFICALDESIGNATION PROJECTNAME CLIENT PREMISES PARISH MONUMENT MUNICIPALITY COUNTY PROVINCE BASEMAP PROJECTMANAGER PARTICIPANTS TYPEOFPROJECT STARTOFPROJECT ENDOFPROJECT MANHOURS MACHINEHOURS AREAOFINVEST COORDINATESYST HEIGHTSYST MASL R1 R2 R3 R4 R5 R6 R7 R8 R9 R10 DOCMETHOD STATE EASTING_MAX EASTING_MIN NORTHING_MIN NORTHING_MAX R13
    PREFETCH_EXHAUSTIVE = No
    DATASET = SiteWorks
    JOIN_KEYS = PROJECT PROJECT
    CACHE_SIZE = 50000
    ODBC2_USER_NAME = sysdba
    FORMAT = ODBC2
    JOINED -> CenterPointReplacer
    JOINED -> Projekt_yta (writer FILEGDB_1)
CenterPointReplacer
    CENTERPOINT -> Projekt_punkt (writer FILEGDB_1)
Projekt_punkt (writer FILEGDB_1)
    attributes: PROJECT text(6), OFFICALDESIGNATION text(12), PROJECTNAME text(64), CLIENT text(64), PREMISES text(64), PARISH text(32), MONUMENT text(6), MUNICIPALITY text(32), COUNTY text(32), PROVINCE text(32), BASEMAP text(32), PROJECTMANAGER text(32), TYPEOFPROJECT text(32), STARTOFPROJECT text(200), ENDOFPROJECT text(200)
Projekt_yta (writer FILEGDB_1)
    attributes: PROJECT text(6), OFFICALDESIGNATION text(12), PROJECTNAME text(64), CLIENT text(64), PREMISES text(64), PARISH text(32), MONUMENT text(6), MUNICIPALITY text(32), COUNTY text(32), PROVINCE text(32), BASEMAP text(32), PROJECTMANAGER text(32), TYPEOFPROJECT text(32), STARTOFPROJECT text(200), ENDOFPROJECT text(200)
GeometryFilter_2
    BREAK_AGG = No
    POINT -> points (writer FILEGDB_1)
    LINE -> lines (writer FILEGDB_1)
    AREA -> polygons (writer FILEGDB_1)
points (writer FILEGDB_1)
    attributes: PROJECT text(200), CATEGORY text(32), TYPENAME text(30), OBJECTNO int, SUBOBJECT int, CLASS text(32)
lines (writer FILEGDB_1)
    attributes: PROJECT text(200), CATEGORY text(32), TYPENAME text(30), OBJECTNO int, SUBOBJECT int, CLASS text(32)
polygons (writer FILEGDB_1)
    attributes: PROJECT text(200), CATEGORY text(32), TYPENAME text(30), OBJECTNO int, SUBOBJECT int, IDX text(32), CLASS text(32)
PROJECT (reader ODBC2_1)
    attributes: PROJECT varchar(6), OFFICALDESIGNATION varchar(12), PROJECTNAME varchar(64), CLIENT varchar(64), PREMISES varchar(64), PARISH varchar(32), MONUMENT varchar(6), MUNICIPALITY varchar(32), COUNTY varchar(32), PROVINCE varchar(32), BASEMAP varchar(32), PROJECTMANAGER varchar(32), PARTICIPANTS clob, TYPEOFPROJECT varchar(32), STARTOFPROJECT timestamp, ENDOFPROJECT timestamp, MANHOURS double, MACHINEHOURS double, AREAOFINVEST double, COORDINATESYST varchar(16), HEIGHTSYST varchar(16), MASL double, R1 smallint, R2 smallint, R3 smallint, R4 smallint, R5 smallint, R6 smallint, R7 smallint, R8 smallint,
      R9 smallint, R10 smallint, DOCMETHOD integer, STATE integer, EASTING_MAX double, EASTING_MIN double, NORTHING_MIN double, NORTHING_MAX double, R13 integer
    -> projektlista (writer XLSXW_1)
projektlista (writer XLSXW_1)
    attributes: Projekt string("column_width;;format_type;Simple;font_type;Arial,9;font_color;;fill_color;;custom_options;<Unused>"), Lst Dnr string("column_width;;format_type;Simple;font_type;Arial,9;font_color;;fill_color;;custom_options;<Unused>"), Benamning string("column_width;;format_type;Simple;font_type;Arial,9;font_color;;fill_color;;custom_options;<Unused>"), Uppdragsgivare string("column_width;;format_type;Simple;font_type;Arial,9;font_color;;fill_color;;custom_options;<Unused>"), Fastighet string("column_width;;format_type;Simple;font_type;Arial,9;font_color;;fill_color;;custom_options;<Unused>"), Socken string("column_width;;format_type;Simple;font_type;Arial,9;font_color;;fill_color;;custom_options;<Unused>"), Fornlamning string("column_width;;format_type;Simple;font_type;Arial,9;font_color;;fill_color;;custom_options;<Unused>"), Kommun string("column_width;;format_type;Simple;font_type;Arial,9;font_color;;fill_color;;custom_options;<Unused>"), Lan string("column_width;;format_type;Simple;font_type;Arial,9;font_color;;fill_color;;custom_options;<Unused>"), Landskap string("column_width;;format_type;Simple;font_type;Arial,9;font_color;;fill_color;;custom_options;<Unused>"), Baskarta string("column_width;;format_type;Simple;font_type;Arial,9;font_color;;fill_color;;custom_options;<Unused>"), Projektledare string("column_width;;format_type;Simple;font_type;Arial,9;font_color;;fill_color;;custom_options;<Unused>"), Deltagare string("column_width;;format_type;Simple;font_type;Arial,9;font_color;;fill_color;;custom_options;<Unused>"), Undersokningstyp string("column_width;;format_type;Simple;font_type;Arial,9;font_color;;fill_color;;custom_options;<Unused>"), Projektstart datetime("column_width;;format_type;Simple;font_type;Arial,9;font_color;;fill_color;;custom_options;<Unused>"), Projektslut datetime("column_width;;format_type;Simple;font_type;Arial,9;font_color;;fill_color;;custom_options;<Unused>"), Mantimmar number("column_width;;format_type;Simple;font_type;Arial,9;font_color;;fill_color;;custom_options;<Unused>"), Maskintimmar number("column_width;;format_type;Simple;font_type;Arial,9;font_color;;fill_color;;custom_options;<Unused>"), Undersokt yta number("column_width;;format_type;Simple;font_type;Arial,9;font_color;;fill_color;;custom_options;<Unused>"), Koordinatsystem string("column_width;;format_type;Simple;font_type;Arial,9;font_color;;fill_color;;custom_options;<Unused>"), Hojdsystem string("column_width;;format_type;Simple;font_type;Arial,9;font_color;;fill_color;;custom_options;<Unused>"), H.o.h. number("column_width;;format_type;Simple;font_type;Arial,9;font_color;;fill_color;;custom_options;<Unused>"), Dokumentationsmetod number("column_width;;format_type;Simple;font_type;Arial,9;font_color;;fill_color;;custom_options;<Unused>"), STATE number("column_width;;format_type;Simple;font_type;Arial,9;font_color;;fill_color;;custom_options;<Unused>")

FME custom transformer LoopFilter
Tests whether a line is a loop, i.e. whether its end matches the beginning.
The transformers outputs loops through PASSED port, and non-loops through FAILED port.
An isLoop attribute is added to each feature. 1 means the feature is loop, and zero means it is not.
Copyright (c) 2012 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

LINE (input)
    -> LineFilter
Note: LoopFilter / Dmitri Bagh / July 11, 2005
LineFilter: GeometryFilter
    LINE -> LoopTester
    POINT -> NON-LINEAR (output)
    ARC -> NON-LINEAR (output)
    AREA -> NON-LINEAR (output)
    ELLIPSE -> NON-LINEAR (output)
    TEXT -> NON-LINEAR (output)
    NULL -> NON-LINEAR (output)
Note: LoopTester [ExpressionEvaluator] / _isLoop = (@Coordinate(x,0)-@Coordinate(x,-1))||(@Coordinate(y,0)-@Coordinate(y,-1))
Note: Evaluates to 0 if feature is loop, and 1, if it is not.
LoopTester: ExpressionEvaluator
    VAL_ATTR = _isLoop
    EXPRESSION = (@Coordinate(x,0)-@Coordinate(x,-1))||(@Coordinate(y,0)-@Coordinate(y,-1))
    -> TESTER
Note: TESTER [Tester] / Test Description: / TEST &_isLoop = 0 / Condition: OR / Composite Test Expression:
TESTER: Tester
    TEST_MODE = Automatic
    BOOL_OP = OR
    TEST_LIST = &_isLoop,=,0
    TEST_CLAUSE = TEST &_isLoop = 0
    PASSED -> PASSED (output)
    FAILED -> FAILED (output)
PASSED (output)
FAILED (output)
NON-LINEAR (output)
