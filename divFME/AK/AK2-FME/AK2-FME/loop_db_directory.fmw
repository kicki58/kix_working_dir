FME workspace loop_db_directory.fmw

Parameters:
- SourceDataset_PATH = C:\Projekt\Siteworks_db   # Directory
- dbname = .   # databas

Readers:
- PATH_1: PATH from $(SourceDataset_PATH)

PATH (reader PATH_1)
    attributes: path_unix buffer, path_windows buffer, path_rootname buffer, path_filename buffer, path_extension buffer, path_directory_unix buffer, path_directory_windows buffer, path_type char(10)
    -> AttributeCreator
AttributeCreator
    ATTR_LIST = dbname,@Value(path_windows)
    -> PythonCaller_2
PythonCaller_2
    PYTHONSYMBOL = FeatureProcessor
    NEW_ATTRIBUTES = $(dbname)
    PYTHONSOURCE:
      import fme
      import fmeobjects
      from _winreg import *
      # Template Function interface:
      def processFeature(feature):
          pass

      # Template Class Interface:
      class FeatureProcessor(object):
          def __init__(self):
              pass
          def input(self,feature):
              try:
                  dbn=feature.getAttribute("path_windows")
      #           dbn=FME_MacroValues['dbname']
                  keyval=r"SOFTWARE\ODBC\ODBC.INI\SiteWorks"
                  Registrykey= OpenKey(HKEY_CURRENT_USER, keyval, 0,KEY_WRITE)
                  SetValueEx(Registrykey,"Dbname",0,REG_SZ,"localhost:"+dbn)
                  CloseKey(Registrykey)
              except WindowsError:
                  return False
              self.pyoutput(feature)

          def close(self):
              pass
    -> WorkspaceRunner
WorkspaceRunner
    WORKSPACE_PARAMETERS = DestDataset_FILEGDB,c:\Siteworks.gdb,SourceDataset_ODBC2_3,SiteWorks,DestDataset_SHAPE,$(FME_MF_DIR_USERTYPED)AK,dbname,C:\Projekt\Siteworks_db\2067 Irsta U.SWDB,DestDataset_FILEGDB_9,C:\Siteworks.gdb,DestDataset_FILEGDB_7,projekt_yta,DestDataset_FILEGDB_11,Siteworks,DestDataset_XLSXW,P:\RAÄ_arkeologisk_dokumentation\Steg3\AK\projektlista_FME_newrun.xlsx,DestDataset_FILEGDB_8,Siteworks,DestDataset_FILEGDB_10,Siteworks,SourceDataset_ODBC2,SiteWorks
    WORKSPACE_FILE = $(FME_MF_DIR)SiteWorks_4_2013_3.fmw
    BLOCKING = Yes
    FAILED -> AttributeCreator_2
AttributeCreator_2
    ATTR_LIST = error,@Value(_failure_message)
    -> Logger
Logger
    FEATURE_TYPE = $(SourceDataset_PATH)
    MAXCOORDS = 20
    MAXFEATS = 20
    MESSAGE = Error! Feature is:
