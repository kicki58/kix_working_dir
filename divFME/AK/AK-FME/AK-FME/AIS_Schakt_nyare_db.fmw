FME workspace AIS_Schakt_nyare_db.fmw

Parameters:
- DestDataset_SHAPE = D:\Projekt\RAA_Arkeologiska_data\Bearb\AK\AIS   # Destination Esri Shape Folder
- SourceDataset_CSV = D:\Projekt\RAA_Arkeologiska_data\Bearb\AK\AIS_nyare_Db\SCHKTLOK.csv   # Source CSV (Comma Separated Value) File(s)
- SourceDataset_CSV_5 = D:\Projekt\RAA_Arkeologiska_data\Bearb\AK\AIS_nyare_Db\SCHKTLST.csv   # Source CSV (Comma Separated Value) File(s)
- SourceDataset_CSV_7 = D:\Projekt\RAA_Arkeologiska_data\Bearb\AK\AIS_nyare_Db\PROJEKT.csv   # Source CSV (Comma Separated Value) File(s)
- DestDataset_ESRISHAPE = D:\Projekt\RAA_Arkeologiska_data\Bearb\AK\AIS_nyare_Db   # Destination Esri Shapefile Folder
- SourceDataset_CSV_6 = D:\Projekt\RAA_Arkeologiska_data\Bearb\AK\AIS_nyare_Db\RUTOR.csv   # Source CSV (Comma Separated Value) File(s)
- DestDataset_XLSXW = D:\Projekt\RAA_Arkeologiska_data\Bearb\AK\AIS_nyare_Db\Projekt.xlsx   # Destination Microsoft Excel File

Readers:
- CSV_1: CSV from $(SourceDataset_CSV) in EPSG:2400
- CSV_2: CSV from $(SourceDataset_CSV_5) in EPSG:2400
- CSV_3: CSV from $(SourceDataset_CSV_7)
- CSV_4: CSV from $(SourceDataset_CSV_6)

Writers:
- SHAPE_1: SHAPE to $(DestDataset_SHAPE)
- ESRISHAPE_2: ESRISHAPE to $(DestDataset_ESRISHAPE) in EPSG:3006
- XLSXW_1: XLSXW to $(DestDataset_XLSXW)

CSV (reader CSV_1)
    attributes: Projektnummer char(7), Delprojektnummer number(2,0), Schaktnummer number(4,0), Punktnummer number(3,0), X number(12,4), Y number(12,4), Z number(7,4)
    -> Tester
    -> CSV_2
CSV_2: Inspector
CSV (reader CSV_4)
    attributes: Projektnummer char(7), Delprojektnummer number(3,0), Ruta char(7), X number(11,3), Y number(11,3), Z number(7,3), Rutstorlek number(2,0), Inmätningsfil char(1), Datum char(11), Signum char(4)
    -> Tester
    -> CSV
Tester
    TEST_DESCRIPTION = ""
    BOOL_OP = OR
    TEST_CLAUSE = TEST @Value(X) < 200000
    TEST_MODE = Automatic
    PASSED -> AttributeReprojector
    FAILED -> AttributeCreator_2
AttributeReprojector
    DEST = EPSG:2400
    YATTR = Y
    XATTR = X
    SOURCE = EPSG:3152
    -> AttributeCreator
AttributeCreator_2
    ATTR_TABLE:
      SET_TO X = @Value(X)+1000000
      SET_TO Y = @Evaluate(@Value(Y)+6000000)
    -> AttributeCreator
AttributeCreator
    ATTR_LIST = E,@Value(X),N,@Value(Y)
    -> VertexCreator
VertexCreator
    XVAL = @Value(E)
    ZVAL = @Value(Z)
    MODE_NAME = Add Point
    INDEX = 0
    YVAL = @Value(N)
    -> Tester_2
Tester_2
    TEST_DESCRIPTION = ""
    BOOL_OP = OR
    TEST_CLAUSE = TEST Ruta ATTRIBUTE_IS_MISSING ""
    TEST_MODE = Automatic
    PASSED -> PointConnector
    FAILED -> FeatureMerger [REQUESTOR]
PointConnector
    BREAKATTR = Schaktnummer Delprojektnummer Projektnummer
    LINE -> LineCloser
LineCloser
    FORCE_CLOSE_Z_CASES = No
    AREA -> FeatureMerger [REQUESTOR]
CSV: Inspector
CSV (reader CSV_3)
    attributes: Projektnummer char(7), Delprojektnummer char(7), Kategori char(26), Plats char(31), Fastighet/kvarter char(47), Kommun char(22), Socken char(23), Landskap char(18), Län char(19), Fornlämningsnummer char(16), Länsstyrelsens beslutsnr char(16), Arbetsperiod char(30), Arbetstimmar char(10), Maskintimmar char(9), Objektets storlek char(18), Ekonomisk karta char(22), Koordinatsystem char(24), Höjdsystem char(12), Lägesangivelse norr number(13,4), Lägesangivelse öster number(13,4), M.ö.h. number(6,2), Uppdragsgivare char(35), Ansvarig grävledare char(25), RAÄs diarienummer char(14), Projekt låst char(6), Mätpunkt i rutor char(1)
    -> FeatureMerger_2 [SUPPLIER]
    -> Projektlista (writer XLSXW_1)
Projektlista (writer XLSXW_1)
    attributes: Projektnummer string(7), Delprojektnummer string(7), Kategori string(26), Plats string(31), Fastighet/kvarter string(47), Kommun string(22), Socken string(23), Landskap string(18), Län string(19), Fornlämningsnummer string(16), Länsstyrelsens beslutsnr string(16), Arbetsperiod string(30), Arbetstimmar string(10), Maskintimmar string(9), Objektets storlek string(18), Ekonomisk karta string(22), Koordinatsystem string(24), Höjdsystem string(12), Lägesangivelse norr number(13), Lägesangivelse öster number(13), M.ö.h. number(6), Uppdragsgivare string(35), Ansvarig grävledare string(25), RAÄs diarienummer string(14), Projekt låst string(6), Mätpunkt i rutor string(1)
CSV (reader CSV_2)
    attributes: Projektnummer char(7), Delprojektnummer number(3,0), Schaktnummer number(5,0), Typ char(24), Jordart i botten char(21), Djup number(6,2), Area number(10,4), Kommentar char(103), Inmätningsfil char(13), Signum char(4), Registreringsdatum char(11)
    -> FeatureMerger [SUPPLIER]
FeatureMerger
    JOIN_KEYS = @Value(Projektnummer) @Value(Projektnummer) AUTO @Value(Delprojektnummer) @Value(Delprojektnummer) AUTO
    SUPPLIERS_FIRST = No
    ATTR_ACCUM_MODE = Merge Supplier
    ATTR_CONFLICT_RES = Use Requestor
    REJECT_NULL_MISSING_KEYS = No
    MERGE_TYPE = Attributes Only
    IGNORE_NULLS = No
    PROCESS_DUPS = No
    MERGED -> FeatureMerger_2 [REQUESTOR]
FeatureMerger_2
    JOIN_KEYS = @Value(Projektnummer) @Value(Projektnummer) AUTO @Value(Delprojektnummer) @Value(Delprojektnummer) AUTO
    SUPPLIERS_FIRST = No
    ATTR_ACCUM_MODE = Merge Supplier
    ATTR_CONFLICT_RES = Use Requestor
    REJECT_NULL_MISSING_KEYS = No
    MERGE_TYPE = Attributes Only
    IGNORE_NULLS = No
    PROCESS_DUPS = No
    MERGED -> Reprojector
    MERGED -> Aggregator
Reprojector
    DEST = EPSG:3006
    RASTER_CELL_SIZE = Preserve Cells
    INTERPOLATION_TYPE_NAME = Nearest Neighbor
    SOURCE = EPSG:2400
    REPROJECTED -> GeometryFilter
GeometryFilter
    GEOM_PORT_NAMES = Point Area
    BREAK_AGG = No
    POINT -> rutor_AIS_nyare (writer SHAPE_1)
    AREA -> schakt_AIS_nyare_db (writer SHAPE_1)
rutor_AIS_nyare (writer SHAPE_1)
    attributes: Projektnum char(254), Delprojekt char(254), Ruta char(16), X char(11), Y number(10,3), Z number(7,3), Plats char(31), Fastighet_ char(200), Kommun char(22), Socken char(23), Landskap char(18), Län char(19), Fornlämnin char(200), Länsstyrel char(200), Arbetsperi char(200), Arbetstimm char(200), Maskintimm char(200), Objektets_ char(200), Ekonomisk_ char(200), Koordinats char(200), Höjdsystem char(12), Lägesangiv char(200), Lägesang00 char(200), M_ö_h_ char(200), Uppdragsgi char(200), Ansvarig_g char(200), RAÄs_diari char(200)
schakt_AIS_nyare_db (writer SHAPE_1)
    attributes: Projektnum char(254), Delprojekt char(254), Schaktnumm number(16,6), X char(11), Y number(10,3), Z number(7,3), E number(12,3), N number(11,3), Typ char(24), Jordart_i_ char(200), Djup number(6,2), Area number(10,4), Kommentar char(103), Inmätnings char(200), Signum char(4), Registreri char(200), Kategori char(26), Plats char(31), Fastighet_ char(200), Kommun char(22), Socken char(23), Landskap char(18), Län char(19), Fornlämnin char(200), Länsstyrel char(200), Arbetsperi char(200), Arbetstimm char(200), Maskintimm char(200), Objektets_ char(200), Ekonomisk_ char(200),
      Koordinats char(200), Höjdsystem char(12), Lägesangiv char(200), Lägesang00 char(200), M_ö_h_ char(200), Uppdragsgi char(200), Ansvarig_g char(200), RAÄs_diari char(200), Projekt_lå char(200), Mätpunkt_i char(200)
Aggregator
    AGGREGATE_TYPE = Homogeneous Collection (If Possible)
    ORDERED = No
    ACCUM_ATTRS_NAME = Get Attributes From One Representative Feature
    GROUP_BY = "Ansvarig grävledare" Socken M.ö.h. Arbetsperiod Delprojektnummer Län "Länsstyrelsens beslutsnr" Plats Arbetstimmar "RAÄs diarienummer" Maskintimmar Projektnummer Uppdragsgivare Koordinatsystem Landskap Fornlämningsnummer Höjdsystem "Ekonomisk karta" Fastighet/kvarter Kommun
    SEP = ,
    MODE = Geometry - Assemble One Level
    AGGREGATE -> CenterPointReplacer
CenterPointReplacer
    MODE = Center Point
    POINT -> projektpunkter (writer ESRISHAPE_2)
projektpunkter (writer ESRISHAPE_2)
    attributes: Projektnum char(200), Delprojekt char(200), Plats char(31), Fastighet_ char(200), Kommun char(22), Socken char(23), Landskap char(18), Län char(19), Fornlämnin char(200), Länsstyrel char(200), Arbetsperi char(200), Arbetstimm char(200), Maskintimm char(200), Ekonomisk_ char(200), Koordinats char(200), Höjdsystem char(12), M_ö_h_ char(200), Uppdragsgi char(200), Ansvarig_g char(200), RAÄs_diari char(200)
