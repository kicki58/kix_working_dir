FME workspace 6_createKoordsysExcel.fmw

Parameters:
- SourceDataset_XLSXR = C:\Github\kix\SiteWorks-Py\gpkg_20250325\koordsys.xlsx   # Source Microsoft Excel File(s)

Readers:
- XLSXR_1: XLSXR from $(SourceDataset_XLSXR)

Writers:
- XLSXW_1: XLSXW to $(SourceDataset_XLSXR)

Sheet1 (reader XLSXR_1)
    attributes: gpkg-fil char(93), COORDINATESYST char(15)
    -> DuplicateFilter
DuplicateFilter
    INPUT_ORDERED_CHOICE_LOOKUP = NO
    KEYATTR = COORDINATESYST gpkg-fil
    INPUT_ORDERED_CHOICE = No
    UNIQUE -> DuplicateFilter_2
    UNIQUE -> FeatureMerger [REQUESTOR]
DuplicateFilter_2
    INPUT_ORDERED_CHOICE_LOOKUP = NO
    KEYATTR = gpkg-fil
    INPUT_ORDERED_CHOICE = No
    DUPLICATE -> FeatureMerger [SUPPLIER]
FeatureMerger
    ATTR_ACCUM_MODE = Merge Supplier
    ATTR_CONFLICT_RES_LOOKUP = REQUESTOR_IF_CONFLICT
    CLEANING_TOLERANCE_LOOKUP = AUTO
    CONNECT_Z_MODE_LOOKUP = FIRST_WINS
    GEOM_TYPE_VAL = POLYGONS
    IGNORE_NULLS = No
    JOIN_KEYS = @Value(gpkg-fil) @Value(gpkg-fil) AUTO
    MERGE_TYPE = Attributes Only
    PROCESS_DUPS = YES
    REJECT_NULL_MISSING_KEYS = No
    SUPPLIERS_FIRST = No
    ATTR_CONFLICT_RES = Use Requestor
    CLEANING_TOLERANCE = Automatic
    CONNECT_Z_MODE = First Wins
    GEOM_TYPE = Build Polygons
    MERGED -> AttributeFilter
    UNMERGED_REQUESTOR -> AttributeFilter_2
AttributeFilter
    ATTR_NAME = gpkg-fil
    ATTR_VALUES = <Empty>,<Missing>,<Null>,<Unfiltered>,C:\Github\kix\SiteWorks-Py\gpkg_20250130\2371 Rosersberg SU.gpkg,C:\Github\kix\SiteWorks-Py\gpkg_20250130\2627 Rotebroleden.gpkg,C:\Github\kix\SiteWorks-Py\gpkg_20250130\2713 Sigtuna St Malmg schaktningsövervakning.gpkg,C:\Github\kix\SiteWorks-Py\gpkg_20250130\Projekt.gpkg,C:\Github\kix\SiteWorks-Py\gpkg_20250130\Östergötland.gpkg
    C:\Github\kix\SiteWorks-Py\gpkg_20250130\2371 Rosersberg SU.gpkg -> DuplicateFilter_3
    C:\Github\kix\SiteWorks-Py\gpkg_20250130\2627 Rotebroleden.gpkg -> DuplicateFilter_3
    C:\Github\kix\SiteWorks-Py\gpkg_20250130\2713 Sigtuna St Malmg schaktningsövervakning.gpkg -> DuplicateFilter_3
    C:\Github\kix\SiteWorks-Py\gpkg_20250130\Projekt.gpkg -> DuplicateFilter_3
    C:\Github\kix\SiteWorks-Py\gpkg_20250130\Östergötland.gpkg -> DuplicateFilter_3
DuplicateFilter_3
    INPUT_ORDERED_CHOICE_LOOKUP = NO
    KEYATTR = gpkg-fil
    INPUT_ORDERED_CHOICE = No
    UNIQUE -> AttributeManager_6
AttributeManager_6
    ATTR_TABLE = SET_TO COORDINATESYST (varchar(15)) = RT 90 2,5 gon V
    -> AttributeManager_2
AttributeFilter_2
    ATTR_NAME = COORDINATESYST
    ATTR_VALUES = <Empty>,<Missing>,<Null>,<Unfiltered>,FME_NULL_VALUE,RT90 2,5 gon V,ST74,Sweref,SWEREF,Sweref 99 13 30,SWEREF 99 18.00,sweref 99 TM,Sweref 99 TM,SWEREF 99 TM,SWEREF 99TM,SWEREF99 18.00,Sweref99 TM,SWEREF99 TM,Sweref99TM,SWEREF99TM
    <NULL> -> AttributeManager_3
    RT90 2,5 gon V -> AttributeManager_2
    ST74 -> AttributeManager_3
    Sweref -> AttributeManager_3
    SWEREF -> AttributeManager_3
    Sweref 99 13 30 -> AttributeManager_5
    SWEREF 99 18.00 -> AttributeManager_4
    sweref 99 TM -> AttributeManager
    Sweref 99 TM -> AttributeManager
    SWEREF 99 TM -> AttributeManager
    SWEREF 99TM -> AttributeManager
    SWEREF99 18.00 -> AttributeManager_4
    Sweref99 TM -> AttributeManager
    SWEREF99 TM -> AttributeManager
    Sweref99TM -> AttributeManager
    SWEREF99TM -> AttributeManager
AttributeManager_3
    ATTR_TABLE = SET_TO epsg (int8) = -1
    -> epsg_kod (writer XLSXW_1)
AttributeManager_2
    ATTR_TABLE = SET_TO epsg (varchar(9)) = EPSG:3021
    -> epsg_kod (writer XLSXW_1)
AttributeManager_5
    ATTR_TABLE = SET_TO epsg (varchar(9)) = EPSG:3008
    -> epsg_kod (writer XLSXW_1)
AttributeManager_4
    ATTR_TABLE = SET_TO epsg (varchar(9)) = EPSG:3011
    -> epsg_kod (writer XLSXW_1)
AttributeManager
    ATTR_TABLE = SET_TO epsg (varchar(9)) = EPSG:3006
    -> epsg_kod (writer XLSXW_1)
epsg_kod (writer XLSXW_1)
    attributes: gpkg-fil string(93), COORDINATESYST string(15), epsg string(9)
