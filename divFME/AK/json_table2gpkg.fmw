FME workspace json_table2gpkg.fmw

Parameters:
- SourceDataset_JSON_65 = C:\Github\SiteWorks-Py\result\2901 Fyrislund SU\2901 Fyrislund SU\ARCHIVE.json   # Source JSON (JavaScript Object Notation) File or URL
- SourceDataset_JSON_49 = C:\Github\SiteWorks-Py\result\2901 Fyrislund SU\2901 Fyrislund SU\COLOURDE.json   # Source JSON (JavaScript Object Notation) File or URL
- SourceDataset_JSON_41 = C:\Github\SiteWorks-Py\result\2901 Fyrislund SU\2901 Fyrislund SU\DATINGPERIOD.json   # Source JSON (JavaScript Object Notation) File or URL
- SourceDataset_JSON = C:\Github\SiteWorks-Py\result\2901 Fyrislund SU\2901 Fyrislund SU\COUNTY.json   # Source JSON (JavaScript Object Notation) File or URL
- DestDataset_OGCGEOPACKAGE = C:\Github\SiteWorks-Py\result\2901 Fyrislund SU\2901 Fyrislund SU\test3.gpkg   # GeoPackage File
- SourceDataset_JSON_57 = C:\Github\SiteWorks-Py\result\2901 Fyrislund SU\2901 Fyrislund SU\DECORDE.json   # Source JSON (JavaScript Object Notation) File or URL
- SourceDataset_JSON_73 = C:\Github\SiteWorks-Py\result\2901 Fyrislund SU\2901 Fyrislund SU\ELMTYPE.json   # Source JSON (JavaScript Object Notation) File or URL
- SourceDataset_JSON_53 = C:\Github\SiteWorks-Py\result\2901 Fyrislund SU\2901 Fyrislund SU\MATDE.json   # Source JSON (JavaScript Object Notation) File or URL
- SourceDataset_JSON_45 = C:\Github\SiteWorks-Py\result\2901 Fyrislund SU\2901 Fyrislund SU\MTYPE.json   # Source JSON (JavaScript Object Notation) File or URL
- SourceDataset_JSON_61 = C:\Github\SiteWorks-Py\result\2901 Fyrislund SU\2901 Fyrislund SU\MUNICIPALITY.json   # Source JSON (JavaScript Object Notation) File or URL
- SourceDataset_JSON_69 = C:\Github\SiteWorks-Py\result\2901 Fyrislund SU\2901 Fyrislund SU\OBJ.json   # Source JSON (JavaScript Object Notation) File or URL
- SourceDataset_JSON_39 = C:\Github\SiteWorks-Py\result\2901 Fyrislund SU\2901 Fyrislund SU\OBJDETAIL.json   # Source JSON (JavaScript Object Notation) File or URL
- SourceDataset_JSON_43 = C:\Github\SiteWorks-Py\result\2901 Fyrislund SU\2901 Fyrislund SU\OBJTYPPROJ.json   # Source JSON (JavaScript Object Notation) File or URL
- SourceDataset_JSON_47 = C:\Github\SiteWorks-Py\result\2901 Fyrislund SU\2901 Fyrislund SU\OSTEOLOGY.json   # Source JSON (JavaScript Object Notation) File or URL
- SourceDataset_JSON_51 = C:\Github\SiteWorks-Py\result\2901 Fyrislund SU\2901 Fyrislund SU\OSTREG.json   # Source JSON (JavaScript Object Notation) File or URL
- SourceDataset_JSON_55 = C:\Github\SiteWorks-Py\result\2901 Fyrislund SU\2901 Fyrislund SU\PARTDE.json   # Source JSON (JavaScript Object Notation) File or URL
- SourceDataset_JSON_59 = C:\Github\SiteWorks-Py\result\2901 Fyrislund SU\2901 Fyrislund SU\PATTYP.json   # Source JSON (JavaScript Object Notation) File or URL
- SourceDataset_JSON_63 = C:\Github\SiteWorks-Py\result\2901 Fyrislund SU\2901 Fyrislund SU\PROCESSDE.json   # Source JSON (JavaScript Object Notation) File or URL
- SourceDataset_JSON_67 = C:\Github\SiteWorks-Py\result\2901 Fyrislund SU\2901 Fyrislund SU\PROJSTA.json   # Source JSON (JavaScript Object Notation) File or URL
- SourceDataset_JSON_71 = C:\Github\SiteWorks-Py\result\2901 Fyrislund SU\2901 Fyrislund SU\PROJTASK.json   # Source JSON (JavaScript Object Notation) File or URL
- SourceDataset_JSON_38 = C:\Github\SiteWorks-Py\result\2901 Fyrislund SU\2901 Fyrislund SU\QUERIE.json   # Source JSON (JavaScript Object Notation) File or URL
- SourceDataset_JSON_40 = C:\Github\SiteWorks-Py\result\2901 Fyrislund SU\2901 Fyrislund SU\RELATION.json   # Source JSON (JavaScript Object Notation) File or URL
- SourceDataset_JSON_42 = C:\Github\SiteWorks-Py\result\2901 Fyrislund SU\2901 Fyrislund SU\SHAPEDE.json   # Source JSON (JavaScript Object Notation) File or URL
- SourceDataset_JSON_44 = C:\Github\SiteWorks-Py\result\2901 Fyrislund SU\2901 Fyrislund SU\SPECREGDE.json   # Source JSON (JavaScript Object Notation) File or URL
- SourceDataset_JSON_46 = C:\Github\SiteWorks-Py\result\2901 Fyrislund SU\2901 Fyrislund SU\STA.json   # Source JSON (JavaScript Object Notation) File or URL
- SourceDataset_JSON_48 = C:\Github\SiteWorks-Py\result\2901 Fyrislund SU\2901 Fyrislund SU\SYSDATA.json   # Source JSON (JavaScript Object Notation) File or URL
- SourceDataset_JSON_50 = C:\Github\SiteWorks-Py\result\2901 Fyrislund SU\2901 Fyrislund SU\TECHNIQUEDE.json   # Source JSON (JavaScript Object Notation) File or URL
- SourceDataset_JSON_52 = C:\Github\SiteWorks-Py\result\2901 Fyrislund SU\2901 Fyrislund SU\WEARDE.json   # Source JSON (JavaScript Object Notation) File or URL
- SourceDataset_JSON_54 = C:\Github\SiteWorks-Py\result\2901 Fyrislund SU\2901 Fyrislund SU\ACCURACY.json   # Source JSON (JavaScript Object Notation) File or URL
- SourceDataset_JSON_56 = C:\Github\SiteWorks-Py\result\2901 Fyrislund SU\2901 Fyrislund SU\CLASSDE.json   # Source JSON (JavaScript Object Notation) File or URL
- SourceDataset_JSON_58 = C:\Github\SiteWorks-Py\result\2901 Fyrislund SU\2901 Fyrislund SU\DATINGMETHOD.json   # Source JSON (JavaScript Object Notation) File or URL
- SourceDataset_JSON_60 = C:\Github\SiteWorks-Py\result\2901 Fyrislund SU\2901 Fyrislund SU\DEFDE.json   # Source JSON (JavaScript Object Notation) File or URL
- SourceDataset_JSON_64 = C:\Github\SiteWorks-Py\result\2901 Fyrislund SU\2901 Fyrislund SU\OBJECT.json   # Source JSON (JavaScript Object Notation) File or URL
- SourceDataset_JSON_66 = C:\Github\SiteWorks-Py\result\2901 Fyrislund SU\2901 Fyrislund SU\OBJTYP.json   # Source JSON (JavaScript Object Notation) File or URL
- SourceDataset_JSON_68 = C:\Github\SiteWorks-Py\result\2901 Fyrislund SU\2901 Fyrislund SU\PROJECT.json   # Source JSON (JavaScript Object Notation) File or URL
- SourceDataset_JSON_70 = C:\Github\SiteWorks-Py\result\2901 Fyrislund SU\2901 Fyrislund SU\PROJTYPE.json   # Source JSON (JavaScript Object Notation) File or URL
- SourceDataset_JSON_72 = C:\Github\SiteWorks-Py\result\2901 Fyrislund SU\2901 Fyrislund SU\PROVINCE.json   # Source JSON (JavaScript Object Notation) File or URL
- SourceDataset_JSON_62 = C:\Github\SiteWorks-Py\result\2901 Fyrislund SU\2901 Fyrislund SU\OBJDATA.json   # Source JSON (JavaScript Object Notation) File or URL

Readers:
- JSON_2: JSON from $(SourceDataset_JSON_65)
- JSON_3: JSON from $(SourceDataset_JSON_49)
- JSON_1: JSON from $(SourceDataset_JSON)
- JSON_4: JSON from $(SourceDataset_JSON_41)
- JSON_5: JSON from $(SourceDataset_JSON_57)
- JSON_6: JSON from $(SourceDataset_JSON_73)
- JSON_7: JSON from $(SourceDataset_JSON_53)
- JSON_8: JSON from $(SourceDataset_JSON_45)
- JSON_9: JSON from $(SourceDataset_JSON_61)
- JSON_10: JSON from $(SourceDataset_JSON_69)
- JSON_11: JSON from $(SourceDataset_JSON_39)
- JSON_12: JSON from $(SourceDataset_JSON_43)
- JSON_13: JSON from $(SourceDataset_JSON_47)
- JSON_14: JSON from $(SourceDataset_JSON_51)
- JSON_15: JSON from $(SourceDataset_JSON_55)
- JSON_16: JSON from $(SourceDataset_JSON_59)
- JSON_17: JSON from $(SourceDataset_JSON_63)
- JSON_18: JSON from $(SourceDataset_JSON_67)
- JSON_19: JSON from $(SourceDataset_JSON_71)
- JSON_20: JSON from $(SourceDataset_JSON_38)
- JSON_21: JSON from $(SourceDataset_JSON_40)
- JSON_22: JSON from $(SourceDataset_JSON_42)
- JSON_23: JSON from $(SourceDataset_JSON_44)
- JSON_24: JSON from $(SourceDataset_JSON_46)
- JSON_25: JSON from $(SourceDataset_JSON_48)
- JSON_26: JSON from $(SourceDataset_JSON_50)
- JSON_27: JSON from $(SourceDataset_JSON_52)
- JSON_28: JSON from $(SourceDataset_JSON_54)
- JSON_29: JSON from $(SourceDataset_JSON_56)
- JSON_30: JSON from $(SourceDataset_JSON_58)
- JSON_31: JSON from $(SourceDataset_JSON_60)
- JSON_33: JSON from $(SourceDataset_JSON_64)
- JSON_34: JSON from $(SourceDataset_JSON_66)
- JSON_35: JSON from $(SourceDataset_JSON_68)
- JSON_36: JSON from $(SourceDataset_JSON_70)
- JSON_37: JSON from $(SourceDataset_JSON_72)
- JSON_32: JSON from $(SourceDataset_JSON_62)

Writers:
- OGCGEOPACKAGE_1: OGCGEOPACKAGE to $(DestDataset_OGCGEOPACKAGE)

Note: JSONFeature: PROJECT [JSON]
JSONFeature (reader JSON_35)
    attributes: attribute0 string, attribute1 string, attribute2 string, attribute3 string, attribute4 string, attribute5 string, attribute6 string, attribute7 string, attribute8 string, attribute9 string, attribute10 string, attribute11 string, attribute12 string, attribute13 string, attribute14 string, attribute15 string, attribute16 string, attribute17 string, attribute18 string, attribute19 string, attribute20 string, attribute21 string, attribute22 int, attribute23 int, attribute24 int, attribute25 int, attribute26 int, attribute27 int, attribute28 int, attribute29 int,
      attribute30 int, attribute31 string, attribute32 int, attribute33 int, attribute34 float, attribute35 float, attribute36 float, attribute37 float, attribute38 string
    -> PROJECT (writer OGCGEOPACKAGE_1)
PROJECT (writer OGCGEOPACKAGE_1)
    attributes: attribute0 text, attribute1 text, attribute2 text, attribute3 text, attribute4 text, attribute5 text, attribute6 text, attribute7 text, attribute8 text, attribute9 text, attribute10 text, attribute11 text, attribute12 text, attribute13 text, attribute14 text, attribute15 text, attribute16 text, attribute17 text, attribute18 text, attribute19 text, attribute20 text, attribute21 text, attribute22 int, attribute23 int, attribute24 int, attribute25 int, attribute26 int, attribute27 int, attribute28 int, attribute29 int,
      attribute30 int, attribute31 text, attribute32 int, attribute33 int, attribute34 double, attribute35 double, attribute36 double, attribute37 double, attribute38 text
Note: JSONFeature: OBJDATA [JSON]
JSONFeature (reader JSON_32)
    attributes: attribute0 int, attribute1 string, attribute2 string, attribute3 string, attribute4 int
    -> VertexCreator
VertexCreator
    MEASURE_TYPE = Continuous
    MODE_NAME = Replace with Point
    XVAL = @Value(attribute1)
    YVAL = @Value(attribute2)
    ZVAL = @Value(attribute3)
    -> Aggregator
    -> LineBuilder
Aggregator
    ACCUM_ATTRS_NAME = Drop Incoming Attributes
    AGGREGATE_TYPE = Homogeneous Collection (If Possible)
    COUNT_ATTR = num_of_points
    GROUP_BY = attribute4
    MODE = Geometry - Assemble One Level
    SEP = ,
    AGGREGATE -> FeatureMerger [SUPPLIER]
LineBuilder
    ACCUM_INPUT_ATTRS = Use Attributes From One Feature
    GROUP_BY = attribute4
    REMOVE_DUPLICATES = No
    POINT -> OBJDATA (writer OGCGEOPACKAGE_1)
    LINE -> FeatureMerger [REQUESTOR]
    POLYGON -> OBJDATA (writer OGCGEOPACKAGE_1)
FeatureMerger
    ATTR_ACCUM_MODE = Merge Supplier
    ATTR_CONFLICT_RES = Use Requestor
    IGNORE_NULLS = No
    JOIN_KEYS = @Value(attribute4) @Value(attribute4) AUTO
    MERGE_TYPE = Attributes Only
    PROCESS_DUPS = NO
    REJECT_NULL_MISSING_KEYS = No
    SUPPLIERS_FIRST = No
    MERGED -> TestFilter
Note: om fler än 2 vertex
TestFilter
    DEFAULT_VALUE = <UNFILTERED>
    PASSED_TEST_GROUP_OUTPUT = FIRST
    TEST_LIST = "BOOL_OP,OR,COMPOSITE_TEST,""""""1"""""",TEST_CLAUSE,TEST @Value(num_of_points) > 2",polygon
    polygon -> LineCloser
    <UNFILTERED> -> OBJDATA (writer OGCGEOPACKAGE_1)
LineCloser
    CONNECT_Z_MODE = First Wins
    AREA -> OBJDATA (writer OGCGEOPACKAGE_1)
OBJDATA (writer OGCGEOPACKAGE_1)
    attributes: attribute0 int, attribute1 text, attribute2 text, attribute3 text, attribute4 int, num_of_points int
Note: JSONFeature: SPECREGDE [JSON]
JSONFeature (reader JSON_23)
    attributes: attribute0 int, attribute1 int, attribute2 string
    -> SPECREGDE (writer OGCGEOPACKAGE_1)
SPECREGDE (writer OGCGEOPACKAGE_1)
    attributes: attribute0 int, attribute1 int, attribute2 text
Note: JSONFeature: STA [JSON]
JSONFeature (reader JSON_24)
    attributes: attribute0 string, attribute1 string, attribute2 int
    -> STA (writer OGCGEOPACKAGE_1)
STA (writer OGCGEOPACKAGE_1)
    attributes: attribute0 text, attribute1 text, attribute2 int
Note: JSONFeature: SYSDATA [JSON]
JSONFeature (reader JSON_25)
    attributes: attribute0 int
    -> SYSDATA (writer OGCGEOPACKAGE_1)
SYSDATA (writer OGCGEOPACKAGE_1)
    attributes: attribute0 int
Note: JSONFeature: TECHNIQUEDE [JSON]
JSONFeature (reader JSON_26)
    attributes: attribute0 int, attribute1 string, attribute2 string
    -> TECHNIQUEDE (writer OGCGEOPACKAGE_1)
TECHNIQUEDE (writer OGCGEOPACKAGE_1)
    attributes: attribute0 int, attribute1 text, attribute2 text
Note: JSONFeature: WEARDE [JSON]
JSONFeature (reader JSON_27)
    attributes: attribute0 int, attribute1 string, attribute2 string
    -> WEARDE (writer OGCGEOPACKAGE_1)
WEARDE (writer OGCGEOPACKAGE_1)
    attributes: attribute0 int, attribute1 text, attribute2 text
Note: JSONFeature: ACCURACY [JSON]
JSONFeature (reader JSON_28)
    attributes: attribute0 string, attribute1 string, attribute2 string, attribute3 string
    -> ACCURACY (writer OGCGEOPACKAGE_1)
ACCURACY (writer OGCGEOPACKAGE_1)
    attributes: attribute0 text, attribute1 text, attribute2 text, attribute3 text
Note: JSONFeature: CLASSDE [JSON]
JSONFeature (reader JSON_29)
    attributes: attribute0 int, attribute1 string, attribute2 string, attribute3 string
    -> CLASSDE (writer OGCGEOPACKAGE_1)
CLASSDE (writer OGCGEOPACKAGE_1)
    attributes: attribute0 int, attribute1 text, attribute2 text, attribute3 text
Note: JSONFeature: DATINGMETHOD [JSON]
JSONFeature (reader JSON_30)
    attributes: attribute0 int, attribute1 string, attribute2 string
    -> DATINGMETHOD (writer OGCGEOPACKAGE_1)
DATINGMETHOD (writer OGCGEOPACKAGE_1)
    attributes: attribute0 int, attribute1 text, attribute2 text
Note: JSONFeature: DEFDE [JSON]
JSONFeature (reader JSON_31)
    attributes: attribute0 int, attribute1 string, attribute2 string
    -> DEFDE (writer OGCGEOPACKAGE_1)
DEFDE (writer OGCGEOPACKAGE_1)
    attributes: attribute0 int, attribute1 text, attribute2 text
Note: JSONFeature: OBJECT [JSON]
JSONFeature (reader JSON_33)
    attributes: attribute0 string, attribute1 string, attribute2 int, attribute3 int, attribute4 int, attribute5 string, attribute6 string, attribute7 string, attribute8 string, attribute9 string, attribute10 string, attribute11 string, attribute12 string, attribute13 string, attribute14 int, attribute15 string, attribute16 string, attribute17 string, attribute18 string, attribute19 string, attribute20 string, attribute21 string, attribute22 string, attribute23 string, attribute24 string, attribute25 string, attribute26 string, attribute27 string, attribute28 string, attribute29 string,
      attribute30 string, attribute31 string, attribute32 string, attribute33 string, attribute34 string, attribute35 string, attribute36 string, attribute37 string, attribute38 string, attribute39 string, attribute40 string, attribute41 string, attribute42 string, attribute43 string, attribute44 string, attribute45 string, attribute46 string, attribute47 string, attribute48 string, attribute49 string, attribute50 string, attribute51 string, attribute52 string, attribute53 string, attribute54 string, attribute55 string, attribute56 string, attribute57 string, attribute58 string, attribute59 string,
      attribute60 string, attribute61 string, attribute62 string, attribute63 string, attribute64 string, attribute65 string, attribute66 string, attribute67 string, attribute68 string, attribute69 string, attribute70 string, attribute71 string, attribute72 string, attribute73 string, attribute74 string, attribute75 string, attribute76 string, attribute77 string, attribute78 string, attribute79 string, attribute80 string, attribute81 string, attribute82 string, attribute83 string, attribute84 string, attribute85 string, attribute86 string, attribute87 string, attribute88 string, attribute89 string,
      attribute90 string, attribute91 string, attribute92 string, attribute93 string, attribute94 string, attribute95 string, attribute96 string, attribute97 string, attribute98 string, attribute99 string, attribute100 string, attribute101 string, attribute102 string, attribute103 int, attribute104 string, attribute105 string, attribute106 string, attribute107 string, attribute108 string, attribute109 string, attribute110 int, attribute111 string, attribute112 string, attribute113 string, attribute114 string, attribute115 string, attribute116 string, attribute117 string, attribute118 string, attribute119 string,
      attribute120 string, attribute121 string, attribute122 string, attribute123 string, attribute124 string, attribute125 string, attribute126 string, attribute127 string, attribute128 string, attribute129 string, attribute130 string, attribute131 string
    -> OBJECT (writer OGCGEOPACKAGE_1)
OBJECT (writer OGCGEOPACKAGE_1)
    attributes: attribute0 text, attribute1 text, attribute2 int, attribute3 int, attribute4 int, attribute5 text, attribute6 text, attribute7 text, attribute8 text, attribute9 text, attribute10 text, attribute11 text, attribute12 text, attribute13 text, attribute14 int, attribute15 text, attribute16 text, attribute17 text, attribute18 text, attribute19 text, attribute20 text, attribute21 text, attribute22 text, attribute23 text, attribute24 text, attribute25 text, attribute26 text, attribute27 text, attribute28 text, attribute29 text,
      attribute30 text, attribute31 text, attribute32 text, attribute33 text, attribute34 text, attribute35 text, attribute36 text, attribute37 text, attribute38 text, attribute39 text, attribute40 text, attribute41 text, attribute42 text, attribute43 text, attribute44 text, attribute45 text, attribute46 text, attribute47 text, attribute48 text, attribute49 text, attribute50 text, attribute51 text, attribute52 text, attribute53 text, attribute54 text, attribute55 text, attribute56 text, attribute57 text, attribute58 text, attribute59 text,
      attribute60 text, attribute61 text, attribute62 text, attribute63 text, attribute64 text, attribute65 text, attribute66 text, attribute67 text, attribute68 text, attribute69 text, attribute70 text, attribute71 text, attribute72 text, attribute73 text, attribute74 text, attribute75 text, attribute76 text, attribute77 text, attribute78 text, attribute79 text, attribute80 text, attribute81 text, attribute82 text, attribute83 text, attribute84 text, attribute85 text, attribute86 text, attribute87 text, attribute88 text, attribute89 text,
      attribute90 text, attribute91 text, attribute92 text, attribute93 text, attribute94 text, attribute95 text, attribute96 text, attribute97 text, attribute98 text, attribute99 text, attribute100 text, attribute101 text, attribute102 text, attribute103 int, attribute104 text, attribute105 text, attribute106 text, attribute107 text, attribute108 text, attribute109 text, attribute110 int, attribute111 text, attribute112 text, attribute113 text, attribute114 text, attribute115 text, attribute116 text, attribute117 text, attribute118 text, attribute119 text,
      attribute120 text, attribute121 text, attribute122 text, attribute123 text, attribute124 text, attribute125 text, attribute126 text, attribute127 text, attribute128 text, attribute129 text, attribute130 text, attribute131 text
Note: JSONFeature: OBJTYP [JSON]
JSONFeature (reader JSON_34)
    attributes: attribute0 int, attribute1 int, attribute2 int, attribute3 string, attribute4 string, attribute5 string, attribute6 string, attribute7 string, attribute8 string, attribute9 int, attribute10 int, attribute11 int, attribute12 int, attribute13 int, attribute14 int, attribute15 int, attribute16 int, attribute17 string, attribute18 string, attribute19 string, attribute20 string, attribute21 string, attribute22 string, attribute23 int, attribute24 int, attribute25 string, attribute26 int, attribute27 int, attribute28 int, attribute29 int,
      attribute30 string, attribute31 string, attribute32 string, attribute33 string, attribute34 string, attribute35 string, attribute36 string, attribute37 string, attribute38 string, attribute39 string, attribute40 string, attribute41 string, attribute42 string, attribute43 string
    -> OBJTYP (writer OGCGEOPACKAGE_1)
OBJTYP (writer OGCGEOPACKAGE_1)
    attributes: attribute0 int, attribute1 int, attribute2 int, attribute3 text, attribute4 text, attribute5 text, attribute6 text, attribute7 text, attribute8 text, attribute9 int, attribute10 int, attribute11 int, attribute12 int, attribute13 int, attribute14 int, attribute15 int, attribute16 int, attribute17 text, attribute18 text, attribute19 text, attribute20 text, attribute21 text, attribute22 text, attribute23 int, attribute24 int, attribute25 text, attribute26 int, attribute27 int, attribute28 int, attribute29 int,
      attribute30 text, attribute31 text, attribute32 text, attribute33 text, attribute34 text, attribute35 text, attribute36 text, attribute37 text, attribute38 text, attribute39 text, attribute40 text, attribute41 text, attribute42 text, attribute43 text
Note: JSONFeature: PROJTYPE [JSON]
JSONFeature (reader JSON_36)
    attributes: attribute0 string, attribute1 string
    -> PROJTYPE (writer OGCGEOPACKAGE_1)
PROJTYPE (writer OGCGEOPACKAGE_1)
    attributes: attribute0 text, attribute1 text
Note: JSONFeature: PROVINCE [JSON]
JSONFeature (reader JSON_37)
    attributes: attribute0 string, attribute1 string
    -> PROVINCE (writer OGCGEOPACKAGE_1)
PROVINCE (writer OGCGEOPACKAGE_1)
    attributes: attribute0 text, attribute1 text
Note: JSONFeature: ARCHIVE [JSON]
JSONFeature (reader JSON_2)
    attributes: attribute0 string, attribute1 string, attribute2 string, attribute3 string, attribute4 string, attribute5 string, attribute6 string, attribute7 string, attribute8 int
    -> ARCHIVE (writer OGCGEOPACKAGE_1)
ARCHIVE (writer OGCGEOPACKAGE_1)
    attributes: attribute0 text, attribute1 text, attribute2 text, attribute3 text, attribute4 text, attribute5 text, attribute6 text, attribute7 text, attribute8 int
Note: JSONFeature: COLOURDE [JSON]
JSONFeature (reader JSON_3)
    attributes: attribute0 int, attribute1 string, attribute2 string
    -> COLOURDE (writer OGCGEOPACKAGE_1)
COLOURDE (writer OGCGEOPACKAGE_1)
    attributes: attribute0 int, attribute1 text, attribute2 text
Note: JSONFeature: COUNTY [JSON]
JSONFeature (reader JSON_1)
    attributes: attribute0 string, attribute1 string
    -> COUNTY (writer OGCGEOPACKAGE_1)
COUNTY (writer OGCGEOPACKAGE_1)
    attributes: attribute0 text, attribute1 text
Note: JSONFeature: DATINGPERIOD [JSON]
JSONFeature (reader JSON_4)
    attributes: attribute0 string, attribute1 string
    -> DATINGPERIOD (writer OGCGEOPACKAGE_1)
DATINGPERIOD (writer OGCGEOPACKAGE_1)
    attributes: attribute0 text, attribute1 text
Note: JSONFeature: DECORDE [JSON]
JSONFeature (reader JSON_5)
    attributes: attribute0 int, attribute1 string, attribute2 string
    -> DECORDE (writer OGCGEOPACKAGE_1)
DECORDE (writer OGCGEOPACKAGE_1)
    attributes: attribute0 int, attribute1 text, attribute2 text
Note: JSONFeature: ELMTYPE [JSON]
JSONFeature (reader JSON_6)
    attributes: attribute0 int, attribute1 string
    -> ELMTYPE (writer OGCGEOPACKAGE_1)
ELMTYPE (writer OGCGEOPACKAGE_1)
    attributes: attribute0 int, attribute1 text
Note: JSONFeature: MATDE [JSON]
JSONFeature (reader JSON_7)
    attributes: attribute0 int, attribute1 string, attribute2 string
    -> MATDE (writer OGCGEOPACKAGE_1)
MATDE (writer OGCGEOPACKAGE_1)
    attributes: attribute0 int, attribute1 text, attribute2 text
Note: JSONFeature: MTYPE [JSON]
JSONFeature (reader JSON_8)
    attributes: attribute0 string, attribute1 string
    -> MTYPE (writer OGCGEOPACKAGE_1)
MTYPE (writer OGCGEOPACKAGE_1)
    attributes: attribute0 text, attribute1 text
Note: JSONFeature: MUNICIPALITY [JSON]
JSONFeature (reader JSON_9)
    attributes: attribute0 string, attribute1 string
    -> MUNICIPALITY (writer OGCGEOPACKAGE_1)
MUNICIPALITY (writer OGCGEOPACKAGE_1)
    attributes: attribute0 text, attribute1 text
Note: JSONFeature: OBJ [JSON]
JSONFeature (reader JSON_10)
    attributes: attribute0 string, attribute1 string, attribute2 int, attribute3 int, attribute4 int, attribute5 string, attribute6 string, attribute7 string, attribute8 string, attribute9 string, attribute10 string, attribute11 string, attribute12 string, attribute13 string, attribute14 int, attribute15 string, attribute16 string, attribute17 string, attribute18 string, attribute19 string, attribute20 string, attribute21 string, attribute22 string, attribute23 string, attribute24 string, attribute25 string, attribute26 string, attribute27 string, attribute28 string, attribute29 string,
      attribute30 string, attribute31 string, attribute32 string, attribute33 string, attribute34 string, attribute35 string, attribute36 string, attribute37 string, attribute38 string, attribute39 string, attribute40 string, attribute41 string, attribute42 string, attribute43 string, attribute44 string, attribute45 string, attribute46 string, attribute47 string, attribute48 string, attribute49 string, attribute50 string, attribute51 string, attribute52 string, attribute53 string, attribute54 string, attribute55 string, attribute56 string, attribute57 string, attribute58 string, attribute59 string,
      attribute60 string, attribute61 string, attribute62 string, attribute63 string, attribute64 string, attribute65 string, attribute66 string, attribute67 string, attribute68 string, attribute69 string, attribute70 string, attribute71 string, attribute72 string, attribute73 string, attribute74 string, attribute75 string, attribute76 string, attribute77 string, attribute78 string, attribute79 string, attribute80 string, attribute81 string, attribute82 string, attribute83 string, attribute84 string, attribute85 string, attribute86 string, attribute87 string, attribute88 string, attribute89 string,
      attribute90 string, attribute91 string, attribute92 string, attribute93 string, attribute94 string, attribute95 string, attribute96 string, attribute97 string, attribute98 string, attribute99 string, attribute100 string, attribute101 string, attribute102 string, attribute103 string, attribute104 string, attribute105 string, attribute106 string, attribute107 string, attribute108 string, attribute109 string, attribute110 string, attribute111 int, attribute112 string, attribute113 string, attribute114 string, attribute115 string, attribute116 string, attribute117 string, attribute118 string, attribute119 string,
      attribute120 int, attribute121 string, attribute122 string, attribute123 string, attribute124 string, attribute125 string, attribute126 string, attribute127 string, attribute128 string, attribute129 string, attribute130 string, attribute131 string, attribute132 string, attribute133 string, attribute134 string, attribute135 string
    -> OBJ (writer OGCGEOPACKAGE_1)
OBJ (writer OGCGEOPACKAGE_1)
    attributes: attribute0 text, attribute1 text, attribute2 int, attribute3 int, attribute4 int, attribute5 text, attribute6 text, attribute7 text, attribute8 text, attribute9 text, attribute10 text, attribute11 text, attribute12 text, attribute13 text, attribute14 int, attribute15 text, attribute16 text, attribute17 text, attribute18 text, attribute19 text, attribute20 text, attribute21 text, attribute22 text, attribute23 text, attribute24 text, attribute25 text, attribute26 text, attribute27 text, attribute28 text, attribute29 text,
      attribute30 text, attribute31 text, attribute32 text, attribute33 text, attribute34 text, attribute35 text, attribute36 text, attribute37 text, attribute38 text, attribute39 text, attribute40 text, attribute41 text, attribute42 text, attribute43 text, attribute44 text, attribute45 text, attribute46 text, attribute47 text, attribute48 text, attribute49 text, attribute50 text, attribute51 text, attribute52 text, attribute53 text, attribute54 text, attribute55 text, attribute56 text, attribute57 text, attribute58 text, attribute59 text,
      attribute60 text, attribute61 text, attribute62 text, attribute63 text, attribute64 text, attribute65 text, attribute66 text, attribute67 text, attribute68 text, attribute69 text, attribute70 text, attribute71 text, attribute72 text, attribute73 text, attribute74 text, attribute75 text, attribute76 text, attribute77 text, attribute78 text, attribute79 text, attribute80 text, attribute81 text, attribute82 text, attribute83 text, attribute84 text, attribute85 text, attribute86 text, attribute87 text, attribute88 text, attribute89 text,
      attribute90 text, attribute91 text, attribute92 text, attribute93 text, attribute94 text, attribute95 text, attribute96 text, attribute97 text, attribute98 text, attribute99 text, attribute100 text, attribute101 text, attribute102 text, attribute103 text, attribute104 text, attribute105 text, attribute106 text, attribute107 text, attribute108 text, attribute109 text, attribute110 text, attribute111 int, attribute112 text, attribute113 text, attribute114 text, attribute115 text, attribute116 text, attribute117 text, attribute118 text, attribute119 text,
      attribute120 int, attribute121 text, attribute122 text, attribute123 text, attribute124 text, attribute125 text, attribute126 text, attribute127 text, attribute128 text, attribute129 text, attribute130 text, attribute131 text, attribute132 text, attribute133 text, attribute134 text, attribute135 text
Note: JSONFeature: OBJDETAIL [JSON]
JSONFeature (reader JSON_11)
    attributes: attribute0 string, attribute1 string, attribute2 int, attribute3 int, attribute4 string, attribute5 string, attribute6 string, attribute7 string, attribute8 string, attribute9 string, attribute10 string, attribute11 string, attribute12 string, attribute13 string, attribute14 string, attribute15 string, attribute16 int, attribute17 int, attribute18 string, attribute19 string, attribute20 string, attribute21 string
    -> OBJDETAIL (writer OGCGEOPACKAGE_1)
OBJDETAIL (writer OGCGEOPACKAGE_1)
    attributes: attribute0 text, attribute1 text, attribute2 int, attribute3 int, attribute4 text, attribute5 text, attribute6 text, attribute7 text, attribute8 text, attribute9 text, attribute10 text, attribute11 text, attribute12 text, attribute13 text, attribute14 text, attribute15 text, attribute16 int, attribute17 int, attribute18 text, attribute19 text, attribute20 text, attribute21 text
Note: JSONFeature: OBJTYPPROJ [JSON]
Note: JSONFeature: OBJTYPPROJ [JSON]
JSONFeature (reader JSON_12)
    attributes: attribute0 int, attribute1 int, attribute2 string
    -> OBJTYPPROJ (writer OGCGEOPACKAGE_1)
OBJTYPPROJ (writer OGCGEOPACKAGE_1)
    attributes: attribute0 int, attribute1 int, attribute2 text
Note: JSONFeature: OSTREG [JSON]
JSONFeature (reader JSON_14)
    attributes: attribute0 string, attribute1 string
    -> OSTREG (writer OGCGEOPACKAGE_1)
OSTREG (writer OGCGEOPACKAGE_1)
    attributes: attribute0 text, attribute1 text
Note: JSONFeature: PARTDE [JSON]
JSONFeature (reader JSON_15)
    attributes: attribute0 int, attribute1 string, attribute2 string, attribute3 string
    -> PARTDE (writer OGCGEOPACKAGE_1)
PARTDE (writer OGCGEOPACKAGE_1)
    attributes: attribute0 int, attribute1 text, attribute2 text, attribute3 text
Note: JSONFeature: PATTYP [JSON]
JSONFeature (reader JSON_16)
    attributes: attribute0 int, attribute1 string
    -> PATTYP (writer OGCGEOPACKAGE_1)
PATTYP (writer OGCGEOPACKAGE_1)
    attributes: attribute0 int, attribute1 text
Note: JSONFeature: PROCESSDE [JSON]
Note: JSONFeature: PROCESSDE [JSON]
JSONFeature (reader JSON_17)
    attributes: attribute0 int, attribute1 string, attribute2 string
    -> PROCESSDE (writer OGCGEOPACKAGE_1)
PROCESSDE (writer OGCGEOPACKAGE_1)
    attributes: attribute0 int, attribute1 text, attribute2 text
Note: JSONFeature: PROJSTA [JSON]
JSONFeature (reader JSON_18)
    attributes: attribute0 string, attribute1 string
    -> PROJSTA (writer OGCGEOPACKAGE_1)
PROJSTA (writer OGCGEOPACKAGE_1)
    attributes: attribute0 text, attribute1 text
Note: JSONFeature: QUERIE [JSON]
JSONFeature (reader JSON_20)
    attributes: attribute0 string, attribute1 string
    -> QUERIE (writer OGCGEOPACKAGE_1)
QUERIE (writer OGCGEOPACKAGE_1)
    attributes: attribute0 text, attribute1 text
Note: JSONFeature: RELATION [JSON]
JSONFeature (reader JSON_21)
    attributes: attribute0 string, attribute1 string, attribute2 int, attribute3 int, attribute4 int, attribute5 int, attribute6 int
    -> RELATION (writer OGCGEOPACKAGE_1)
RELATION (writer OGCGEOPACKAGE_1)
    attributes: attribute0 text, attribute1 text, attribute2 int, attribute3 int, attribute4 int, attribute5 int, attribute6 int
Note: JSONFeature: SHAPEDE [JSON]
JSONFeature (reader JSON_22)
    attributes: attribute0 int, attribute1 string, attribute2 string
    -> SHAPEDE (writer OGCGEOPACKAGE_1)
SHAPEDE (writer OGCGEOPACKAGE_1)
    attributes: attribute0 int, attribute1 text, attribute2 text
