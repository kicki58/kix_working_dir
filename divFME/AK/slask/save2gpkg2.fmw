FME workspace save2gpkg2.fmw
Startup Python:
      import fmeobjects

Parameters:
- db_name = 2824 Fyrislund FU22   # db namn
- DestDataset_OGCGEOPACKAGE = ..\..\SiteWorks-Py\result\$(db_name).gpkg   # GeoPackage File
- SourceDataset_PATH = C:\Github\kix\SiteWorks-Py\result   # INCLUDE_WEB_BROWSER Source Folder and File Pathnames Folder
- SourceDataset_CSV2_43 = ..\..\SiteWorks-Py\result\2824 Fyrislund FU\csv\OBJDATA.csv   # Source CSV (Comma Separated Value) File(s)
- SourceDataset_CSV2_65 = ..\..\SiteWorks-Py\result\2824 Fyrislund FU\csv\ACCURACY.csv   # Source CSV (Comma Separated Value) File(s)
- SourceDataset_CSV2_49 = ..\..\SiteWorks-Py\result\2824 Fyrislund FU\csv\ARCHIVE.csv   # Source CSV (Comma Separated Value) File(s)
- SourceDataset_CSV2_41 = ..\..\SiteWorks-Py\result\2824 Fyrislund FU\csv\COLOURDEF.csv   # Source CSV (Comma Separated Value) File(s)
- SourceDataset_CSV2 = ..\..\SiteWorks-Py\result\2824 Fyrislund FU\csv\CLASSDEF.csv   # Source CSV (Comma Separated Value) File(s)
- SourceDataset_CSV2_57 = ..\..\SiteWorks-Py\result\2824 Fyrislund FU\csv\COUNTY.csv   # Source CSV (Comma Separated Value) File(s)
- SourceDataset_CSV2_73 = ..\..\SiteWorks-Py\result\2824 Fyrislund FU\csv\DATINGMETHODS.csv   # Source CSV (Comma Separated Value) File(s)
- SourceDataset_CSV2_45 = ..\..\SiteWorks-Py\result\2824 Fyrislund FU\csv\DATINGPERIODS.csv   # Source CSV (Comma Separated Value) File(s)
- SourceDataset_CSV2_53 = ..\..\SiteWorks-Py\result\2824 Fyrislund FU\csv\DECORDEF.csv   # Source CSV (Comma Separated Value) File(s)
- SourceDataset_CSV2_61 = ..\..\SiteWorks-Py\result\2824 Fyrislund FU\csv\DEFDEF.csv   # Source CSV (Comma Separated Value) File(s)
- SourceDataset_CSV2_69 = ..\..\SiteWorks-Py\result\2824 Fyrislund FU\csv\ELMTYPE.csv   # Source CSV (Comma Separated Value) File(s)
- SourceDataset_CSV2_39 = ..\..\SiteWorks-Py\result\2824 Fyrislund FU\csv\LAYERS.csv   # Source CSV (Comma Separated Value) File(s)
- SourceDataset_CSV2_47 = ..\..\SiteWorks-Py\result\2824 Fyrislund FU\csv\MATDEF.csv   # Source CSV (Comma Separated Value) File(s)
- SourceDataset_CSV2_51 = ..\..\SiteWorks-Py\result\2824 Fyrislund FU\csv\MTYPES.csv   # Source CSV (Comma Separated Value) File(s)
- SourceDataset_CSV2_55 = ..\..\SiteWorks-Py\result\2824 Fyrislund FU\csv\MUNICIPALITY.csv   # Source CSV (Comma Separated Value) File(s)
- SourceDataset_CSV2_59 = ..\..\SiteWorks-Py\result\2824 Fyrislund FU\csv\OBJ.csv   # Source CSV (Comma Separated Value) File(s)
- SourceDataset_CSV2_63 = ..\..\SiteWorks-Py\result\2824 Fyrislund FU\csv\OBJDETAILS.csv   # Source CSV (Comma Separated Value) File(s)
- SourceDataset_CSV2_67 = ..\..\SiteWorks-Py\result\2824 Fyrislund FU\csv\OBJECTS.csv   # Source CSV (Comma Separated Value) File(s)
- SourceDataset_CSV2_71 = ..\..\SiteWorks-Py\result\2824 Fyrislund FU\csv\OBJTYP.csv   # Source CSV (Comma Separated Value) File(s)
- SourceDataset_CSV2_38 = ..\..\SiteWorks-Py\result\2824 Fyrislund FU\csv\OBJTYPPROJ.csv   # Source CSV (Comma Separated Value) File(s)
- SourceDataset_CSV2_40 = ..\..\SiteWorks-Py\result\2824 Fyrislund FU\csv\PARTDEF.csv   # Source CSV (Comma Separated Value) File(s)
- SourceDataset_CSV2_42 = ..\..\SiteWorks-Py\result\2824 Fyrislund FU\csv\PATTYP.csv   # Source CSV (Comma Separated Value) File(s)
- SourceDataset_CSV2_44 = ..\..\SiteWorks-Py\result\2824 Fyrislund FU\csv\PROCESSDEF.csv   # Source CSV (Comma Separated Value) File(s)
- SourceDataset_CSV2_46 = ..\..\SiteWorks-Py\result\2824 Fyrislund FU\csv\PROJECT.csv   # Source CSV (Comma Separated Value) File(s)
- SourceDataset_CSV2_48 = ..\..\SiteWorks-Py\result\2824 Fyrislund FU\csv\PROJSTAFF.csv   # Source CSV (Comma Separated Value) File(s)
- SourceDataset_CSV2_50 = ..\..\SiteWorks-Py\result\2824 Fyrislund FU\csv\PROJTASK.csv   # Source CSV (Comma Separated Value) File(s)
- SourceDataset_CSV2_52 = ..\..\SiteWorks-Py\result\2824 Fyrislund FU\csv\PROJTYPE.csv   # Source CSV (Comma Separated Value) File(s)
- SourceDataset_CSV2_54 = ..\..\SiteWorks-Py\result\2824 Fyrislund FU\csv\PROVINCE.csv   # Source CSV (Comma Separated Value) File(s)
- SourceDataset_CSV2_56 = ..\..\SiteWorks-Py\result\2824 Fyrislund FU\csv\QUERIES.csv   # Source CSV (Comma Separated Value) File(s)
- SourceDataset_CSV2_58 = ..\..\SiteWorks-Py\result\2824 Fyrislund FU\csv\RELATIONS.csv   # Source CSV (Comma Separated Value) File(s)
- SourceDataset_CSV2_60 = ..\..\SiteWorks-Py\result\2824 Fyrislund FU\csv\SHAPEDEF.csv   # Source CSV (Comma Separated Value) File(s)
- SourceDataset_CSV2_62 = ..\..\SiteWorks-Py\result\2824 Fyrislund FU\csv\SPECREGDEF.csv   # Source CSV (Comma Separated Value) File(s)
- SourceDataset_CSV2_64 = ..\..\SiteWorks-Py\result\2824 Fyrislund FU\csv\STAFF.csv   # Source CSV (Comma Separated Value) File(s)
- SourceDataset_CSV2_66 = ..\..\SiteWorks-Py\result\2824 Fyrislund FU\csv\STRATA.csv   # Source CSV (Comma Separated Value) File(s)
- SourceDataset_CSV2_68 = ..\..\SiteWorks-Py\result\2824 Fyrislund FU\csv\SYSDATA.csv   # Source CSV (Comma Separated Value) File(s)
- SourceDataset_CSV2_70 = ..\..\SiteWorks-Py\result\2824 Fyrislund FU\csv\TECHNIQUEDEF.csv   # Source CSV (Comma Separated Value) File(s)
- SourceDataset_CSV2_72 = ..\..\SiteWorks-Py\result\2824 Fyrislund FU\csv\WEARDEF.csv   # Source CSV (Comma Separated Value) File(s)

Readers:
- CSV2_2: CSV2 from $(SourceDataset_CSV2_65)
- CSV2_3: CSV2 from $(SourceDataset_CSV2_49)
- CSV2_1: CSV2 from $(SourceDataset_CSV2)
- CSV2_4: CSV2 from $(SourceDataset_CSV2_41)
- CSV2_5: CSV2 from $(SourceDataset_CSV2_57)
- CSV2_6: CSV2 from $(SourceDataset_CSV2_73)
- CSV2_7: CSV2 from $(SourceDataset_CSV2_45)
- CSV2_8: CSV2 from $(SourceDataset_CSV2_53)
- CSV2_9: CSV2 from $(SourceDataset_CSV2_61)
- CSV2_10: CSV2 from $(SourceDataset_CSV2_69)
- CSV2_11: CSV2 from $(SourceDataset_CSV2_39)
- CSV2_13: CSV2 from $(SourceDataset_CSV2_47)
- CSV2_14: CSV2 from $(SourceDataset_CSV2_51)
- CSV2_15: CSV2 from $(SourceDataset_CSV2_55)
- CSV2_16: CSV2 from $(SourceDataset_CSV2_59)
- CSV2_17: CSV2 from $(SourceDataset_CSV2_63)
- CSV2_18: CSV2 from $(SourceDataset_CSV2_67)
- CSV2_19: CSV2 from $(SourceDataset_CSV2_71)
- CSV2_20: CSV2 from $(SourceDataset_CSV2_38)
- CSV2_21: CSV2 from $(SourceDataset_CSV2_40)
- CSV2_22: CSV2 from $(SourceDataset_CSV2_42)
- CSV2_23: CSV2 from $(SourceDataset_CSV2_44)
- CSV2_24: CSV2 from $(SourceDataset_CSV2_46)
- CSV2_25: CSV2 from $(SourceDataset_CSV2_48)
- CSV2_26: CSV2 from $(SourceDataset_CSV2_50)
- CSV2_27: CSV2 from $(SourceDataset_CSV2_52)
- CSV2_28: CSV2 from $(SourceDataset_CSV2_54)
- CSV2_29: CSV2 from $(SourceDataset_CSV2_56)
- CSV2_30: CSV2 from $(SourceDataset_CSV2_58)
- CSV2_31: CSV2 from $(SourceDataset_CSV2_60)
- CSV2_32: CSV2 from $(SourceDataset_CSV2_62)
- CSV2_33: CSV2 from $(SourceDataset_CSV2_64)
- CSV2_34: CSV2 from $(SourceDataset_CSV2_66)
- CSV2_35: CSV2 from $(SourceDataset_CSV2_68)
- CSV2_36: CSV2 from $(SourceDataset_CSV2_70)
- CSV2_37: CSV2 from $(SourceDataset_CSV2_72)
- CSV2_12: CSV2 from $(SourceDataset_CSV2_43)
- PATH_1: PATH from $(SourceDataset_PATH)

Writers:
- OGCGEOPACKAGE_1: OGCGEOPACKAGE to $(DestDataset_OGCGEOPACKAGE)

Bookmark: Copy tables
CSV (reader CSV2_3)
    attributes: PROJECT uint32, FILENAME varchar(16), DATEOFRECORDING datetime, PLACEOFRECORDING varchar(11), PERSONINCHARGE varchar(12), COORDINATESYSTEM varchar(12), MEASUREMENTS varchar(39502), FILETYPE varchar(4), FILESTATUS uint32
CSV (reader CSV2_4)
    attributes: OBJECTTYPE uint32, COLOUR varchar(11), DEFAULT_VALUE varchar(2)
    -> Table102 (writer OGCGEOPACKAGE_1)
Table102 (writer OGCGEOPACKAGE_1)
    attributes: OBJECTTYPE int, COLOUR text, DEFAULT_VALUE text
CSV (reader CSV2_5)
    attributes: COUNTY varchar(10), DEFAULT_VALUE varchar(2)
    -> Table10200 (writer OGCGEOPACKAGE_1)
Table10200 (writer OGCGEOPACKAGE_1)
    attributes: COUNTY text, DEFAULT_VALUE text
CSV (reader CSV2_6)
    attributes: DATINGMETHOD uint32, DATINGDESCRIPTION varchar(17), DEFAULT_VALUE varchar(2)
    -> Table10201 (writer OGCGEOPACKAGE_1)
Table10201 (writer OGCGEOPACKAGE_1)
    attributes: DATINGMETHOD int, DATINGDESCRIPTION text, DEFAULT_VALUE text
CSV (reader CSV2_7)
    attributes: PERIOD varchar(30), DEFAULT_VALUE varchar(2)
    -> Table10202 (writer OGCGEOPACKAGE_1)
Table10202 (writer OGCGEOPACKAGE_1)
    attributes: PERIOD text, DEFAULT_VALUE text
CSV (reader CSV2_8)
    attributes: OBJECTTYPE uint32, DECORATION varchar(26), DEFAULT_VALUE varchar(2)
    -> Table10203 (writer OGCGEOPACKAGE_1)
Table10203 (writer OGCGEOPACKAGE_1)
    attributes: OBJECTTYPE int, DECORATION text, DEFAULT_VALUE text
CSV (reader CSV2_9)
    attributes: OBJECTTYPE uint32, DEFDEFINITION varchar(37), DEFAULT_VALUE varchar(2)
    -> Table10204 (writer OGCGEOPACKAGE_1)
Table10204 (writer OGCGEOPACKAGE_1)
    attributes: OBJECTTYPE int, DEFDEFINITION text, DEFAULT_VALUE text
CSV (reader CSV2_10)
    attributes: ELEMENT_TYPE uint32, TYPEDESC varchar(22)
    -> Table10205 (writer OGCGEOPACKAGE_1)
Table10205 (writer OGCGEOPACKAGE_1)
    attributes: ELEMENT_TYPE int, TYPEDESC text
CSV (reader CSV2_11)
    attributes: LAYER string, CLAY string, SILT string, SAND string, GRAVEL string, ROCKS string, BLOCKS string, HUMUS string, COMP_CLAY string, COMP_SILT string, COMP_SAND string, COMP_GRAVEL string, COMP_ROCKS string, COMP_BLOCKS string, COMP_CHARCOAL string, COLOUR string, DEPTH_TOP string, DEPTH_BOTTOM string, PODSOL string, CULTURAL string, BEDROCK string, COMP_BEDROCK string, OBJECTID string
    -> Table10206 (writer OGCGEOPACKAGE_1)
Table10206 (writer OGCGEOPACKAGE_1)
    attributes: LAYER text, CLAY text, SILT text, SAND text, GRAVEL text, ROCKS text, BLOCKS text, HUMUS text, COMP_CLAY text, COMP_SILT text, COMP_SAND text, COMP_GRAVEL text, COMP_ROCKS text, COMP_BLOCKS text, COMP_CHARCOAL text, COLOUR text, DEPTH_TOP text, DEPTH_BOTTOM text, PODSOL text, CULTURAL text, BEDROCK text, COMP_BEDROCK text, OBJECTID text
CSV (reader CSV2_13)
    attributes: OBJECTTYPE uint32, MATERIAL varchar(26), DEFAULT_VALUE varchar(2)
    -> Table1020600 (writer OGCGEOPACKAGE_1)
Table1020600 (writer OGCGEOPACKAGE_1)
    attributes: OBJECTTYPE int, MATERIAL text, DEFAULT_VALUE text
CSV (reader CSV2_14)
    attributes: EXTENSION varchar(4), FILETYPE varchar(23)
    -> Table1020601 (writer OGCGEOPACKAGE_1)
Table1020601 (writer OGCGEOPACKAGE_1)
    attributes: EXTENSION text, FILETYPE text
CSV (reader CSV2_15)
    attributes: MUNICIPALITY varchar(16), DEFAULT_VALUE boolean
    -> Table1020602 (writer OGCGEOPACKAGE_1)
Table1020602 (writer OGCGEOPACKAGE_1)
    attributes: MUNICIPALITY text, DEFAULT_VALUE boolean
CSV (reader CSV2_16)
    attributes: PROJECT uint32, CATEGORY varchar(12), OBJECTNO uint32, SUBOBJECT uint32, TYPENO uint32, DESCRIPTION varchar(1), SUBCLASS varchar(1), DEFINITION varchar(1), INTERPRETATIONS varchar(192), X_AVG x_coordinate, Y_AVG y_coordinate, Z_AVG z_coordinate, OBJLENGTH varchar(1), WIDTH varchar(1), NUMBEROF uint32, WEIGHT varchar(1), BELONGSTO uint32, BELONGSTOSUB uint32, BELONGSTOTYPE varchar(8), CONTEXT varchar(1), CONTEXTOBJECT varchar(1), CONTEXTSUBOBJECT varchar(1), CONTEXTTYPE varchar(1), INCLINATION varchar(1), DATEOFRECORDING datetime, MPRECISION varchar(1), SIGN varchar(33), DATING varchar(1), DATING_MARGINOFERROR varchar(1), DATINGMETHOD varchar(1),
      NONMEASUREDLOCATION varchar(1), MEASUREMENTFILE varchar(16), STRUCKOFF varchar(2), CONSTRUCTION uint32, SUBCONSTRUCTION uint32, ORIENTATION varchar(1), FORM varchar(1), COURNERS varchar(1), HEIGHT varchar(1), RIM varchar(1), BOTTOMRIM varchar(1), BOTTOM varchar(1), SECTION varchar(1), CONDITION varchar(1), SPLITTING varchar(1), TOOLTRACES varchar(1), ASSEMBLY varchar(1), MATERIAL varchar(1), GRANULARITY varchar(1), SURFACE varchar(1), JOINTINGMATERIAL varchar(1), SORTING varchar(1), STRUCTURE varchar(1), CONTENTS varchar(1), CONSISTENCE varchar(1), PACKING varchar(1), COLOUR varchar(1), COMPOSITION varchar(1), JOINTING varchar(1), CHALK varchar(1),
      COAL varchar(1), PEBBELS varchar(1), BRICKFRAG varchar(1), BRICK varchar(1), WOOD varchar(1), CLAY varchar(1), BURNT_CLAY varchar(1), DAUB varchar(1), GRAVEL varchar(1), SOOT varchar(1), ASHES varchar(1), ANIMALBONES varchar(1), FISHBONES varchar(1), ROCKS varchar(1), HUMUS varchar(1), BURNT_BONE varchar(1), UNBURNT_BONE varchar(1), FIRE_CRACKED_ROCK varchar(1), BURNT_STONE varchar(1), MACHINE varchar(1), SHOVEL varchar(1), HOETABLE varchar(1), TROWEL varchar(1), SIEVE varchar(1), PREPARATION varchar(1), CONTAMINATION varchar(1), DROUGHT varchar(1), RAIN varchar(1), FROST varchar(1), WATERSIEVE varchar(1),
      RECORDEDBY varchar(1), VERIFIED varchar(1), OBSERVATIONS varchar(4), CONTACT_ABOVE varchar(1), CONTACT_BELOW varchar(1), SIDE varchar(1), LIMITS varchar(1), MAXHEIGHT varchar(1), DETAILS varchar(1), TAQ varchar(1), TPQ varchar(1), STRATATOP varchar(1), STRATABOTTOM varchar(1), SAND varchar(1), LIME varchar(1), PREV_FUNCTION varchar(1), DATEEDITED datetime, BLAZINGCOLOR varchar(1), FILLING varchar(1), TIERS varchar(1), TIER_DEPTH varchar(1), OBJECTID uint32, BELONGSTOID uint32, CONST_PHASE varchar(1), DEST_PHASE varchar(1), AREA real64, SILT varchar(1), ORGANIC_MATTER varchar(1), BOULDERS varchar(1), NOTES varchar(4),
      IDX uint32, TYPENAME varchar(22), CLASS varchar(11), CONT_CLASS varchar(1), DIAMETER varchar(1), PART varchar(1), INNER_LENGTH varchar(1), INNER_WIDTH varchar(1), INNER_HEIGHT varchar(1), SECTIONS varchar(1), EXAMINATION varchar(1), THICKNESS varchar(1), FRAGMENTS varchar(1)
    -> Table1020603 (writer OGCGEOPACKAGE_1)
Table1020603 (writer OGCGEOPACKAGE_1)
    attributes: PROJECT int, CATEGORY text, OBJECTNO int, SUBOBJECT int, TYPENO int, DESCRIPTION text, SUBCLASS text, DEFINITION text, INTERPRETATIONS text, X_AVG double, Y_AVG double, Z_AVG double, OBJLENGTH text, WIDTH text, NUMBEROF int, WEIGHT text, BELONGSTO int, BELONGSTOSUB int, BELONGSTOTYPE text, CONTEXT text, CONTEXTOBJECT text, CONTEXTSUBOBJECT text, CONTEXTTYPE text, INCLINATION text, DATEOFRECORDING datetime, MPRECISION text, SIGN text, DATING text, DATING_MARGINOFERROR text, DATINGMETHOD text,
      NONMEASUREDLOCATION text, MEASUREMENTFILE text, STRUCKOFF text, CONSTRUCTION int, SUBCONSTRUCTION int, ORIENTATION text, FORM text, COURNERS text, HEIGHT text, RIM text, BOTTOMRIM text, BOTTOM text, SECTION text, CONDITION text, SPLITTING text, TOOLTRACES text, ASSEMBLY text, MATERIAL text, GRANULARITY text, SURFACE text, JOINTINGMATERIAL text, SORTING text, STRUCTURE text, CONTENTS text, CONSISTENCE text, PACKING text, COLOUR text, COMPOSITION text, JOINTING text, CHALK text,
      COAL text, PEBBELS blob, BRICKFRAG text, BRICK text, WOOD text, CLAY text, BURNT_CLAY text, DAUB text, GRAVEL text, SOOT text, ASHES text, ANIMALBONES text, FISHBONES text, ROCKS text, HUMUS text, BURNT_BONE text, UNBURNT_BONE text, FIRE_CRACKED_ROCK text, BURNT_STONE text, MACHINE text, SHOVEL text, HOETABLE text, TROWEL text, SIEVE text, PREPARATION text, CONTAMINATION text, DROUGHT text, RAIN text, FROST text, WATERSIEVE text,
      RECORDEDBY text, VERIFIED text, OBSERVATIONS text, CONTACT_ABOVE text, CONTACT_BELOW text, SIDE text, LIMITS text, MAXHEIGHT text, DETAILS text, TAQ text, TPQ text, STRATATOP text, STRATABOTTOM text, SAND text, LIME text, PREV_FUNCTION text, DATEEDITED datetime, BLAZINGCOLOR text, FILLING text, TIERS text, TIER_DEPTH text, OBJECTID int, BELONGSTOID int, CONST_PHASE text, DEST_PHASE text, AREA double, SILT text, ORGANIC_MATTER text, BOULDERS text, NOTES text,
      IDX int, TYPENAME text, CLASS text, CONT_CLASS text, DIAMETER text, PART text, INNER_LENGTH text, INNER_WIDTH text, INNER_HEIGHT text, SECTIONS text, EXAMINATION text, THICKNESS text, FRAGMENTS text
CSV (reader CSV2_17)
    attributes: PROJECT string, CATEGORY string, OBJECTNO string, SUBOBJECT string, COLOUR string, TECHNIQUE string, WEARMARKS string, PROCESSES string, DECORATION string, SHAPE string, S1 string, S2 string, S3 string, S4 string, S5 string, S6 string, OBJECTID string, IDX string
    -> Table1020604 (writer OGCGEOPACKAGE_1)
Table1020604 (writer OGCGEOPACKAGE_1)
    attributes: PROJECT text, CATEGORY text, OBJECTNO text, SUBOBJECT text, COLOUR text, TECHNIQUE text, WEARMARKS text, PROCESSES text, DECORATION text, SHAPE text, S1 text, S2 text, S3 text, S4 text, S5 text, S6 text, OBJECTID text, IDX text
CSV (reader CSV2_18)
    attributes: PROJECT uint32, CATEGORY varchar(12), OBJECTNO uint32, SUBOBJECT uint32, TYPENO uint32, DESCRIPTION varchar(1), SUBCLASS varchar(1), DEFINITION varchar(1), INTERPRETATIONS varchar(192), X_AVG x_coordinate, Y_AVG y_coordinate, Z_AVG z_coordinate, OBJLENGTH varchar(1), WIDTH varchar(1), NUMBEROF uint32, WEIGHT varchar(1), BELONGSTO uint32, BELONGSTOSUB uint32, BELONGSTOTYPE varchar(8), CONTEXT varchar(1), CONTEXTOBJECT varchar(1), CONTEXTSUBOBJECT varchar(1), CONTEXTTYPE varchar(1), INCLINATION varchar(1), DATEOFRECORDING datetime, MPRECISION varchar(1), SIGN varchar(33), DATING varchar(1), DATINGMETHOD varchar(1), NONMEASUREDLOCATION varchar(1),
      MEASUREMENTFILE varchar(16), STRUCKOFF varchar(2), CONSTRUCTION uint32, SUBCONSTRUCTION uint32, ORIENTATION varchar(1), FORM varchar(1), COURNERS varchar(1), HEIGHT varchar(1), RIM varchar(1), BOTTOMRIM varchar(1), BOTTOM varchar(1), SECTION varchar(1), CONDITION varchar(1), SPLITTING varchar(1), TOOLTRACES varchar(1), ASSEMBLY varchar(1), MATERIAL varchar(1), GRANULARITY varchar(1), SURFACE varchar(1), JOINTINGMATERIAL varchar(1), SORTING varchar(1), STRUCTURE varchar(1), CONTENTS varchar(1), CONSISTENCE varchar(1), PACKING varchar(1), COLOUR varchar(1), COMPOSITION varchar(1), JOINTING varchar(1), CHALK varchar(1), COAL varchar(1),
      PEBBELS varchar(1), BRICKFRAG varchar(1), BRICK varchar(1), WOOD varchar(1), CLAY varchar(1), BURNT_CLAY varchar(1), DAUB varchar(1), GRAVEL varchar(1), SOOT varchar(1), ASHES varchar(1), ANIMALBONES varchar(1), FISHBONES varchar(1), MACHINE varchar(1), SHOVEL varchar(1), HOETABLE varchar(1), TROWEL varchar(1), SIEVE varchar(1), PREPARATION varchar(1), CONTAMINATION varchar(1), DROUGHT varchar(1), RAIN varchar(1), FROST varchar(1), WATERSIEVE varchar(1), RECORDEDBY varchar(1), VERIFIED varchar(1), OBSERVATIONS varchar(4), CONTACT_BELOW varchar(1), SIDE varchar(1), LIMITS varchar(1), MAXHEIGHT varchar(1),
      DETAILS varchar(1), TAQ varchar(1), TPQ varchar(1), STRATATOP varchar(1), STRATABOTTOM varchar(1), SAND varchar(1), LIME varchar(1), PREV_FUNCTION varchar(1), DATEEDITED datetime, BLAZINGCOLOR varchar(1), FILLING varchar(1), TIERS varchar(1), TIER_DEPTH varchar(1), OBJECTID uint32, BELONGSTOID uint32, CONST_PHASE varchar(1), DEST_PHASE varchar(1), AREA real64, SILT varchar(1), ORGANIC_MATTER varchar(1), IDX uint32, NOTES varchar(4), DIAMETER varchar(1), ROCKS varchar(1), HUMUS varchar(1), BURNT_BONE varchar(1), UNBURNT_BONE varchar(1), FIRE_CRACKED_ROCK varchar(1), BURNT_STONE varchar(1), PART varchar(1),
      DATING_MARGINOFERROR varchar(1), BOULDERS varchar(1), CONTACT_ABOVE varchar(1), INNER_LENGTH varchar(1), INNER_WIDTH varchar(1), INNER_HEIGHT varchar(1), SECTIONS varchar(1), EXAMINATION varchar(1), FRAGMENTS varchar(1), THICKNESS varchar(1)
    -> Table1020605 (writer OGCGEOPACKAGE_1)
Table1020605 (writer OGCGEOPACKAGE_1)
    attributes: PROJECT int, CATEGORY text, OBJECTNO int, SUBOBJECT int, TYPENO int, DESCRIPTION text, SUBCLASS text, DEFINITION text, INTERPRETATIONS text, X_AVG double, Y_AVG double, Z_AVG double, OBJLENGTH text, WIDTH text, NUMBEROF int, WEIGHT text, BELONGSTO int, BELONGSTOSUB int, BELONGSTOTYPE text, CONTEXT text, CONTEXTOBJECT text, CONTEXTSUBOBJECT text, CONTEXTTYPE text, INCLINATION text, DATEOFRECORDING datetime, MPRECISION text, SIGN text, DATING text, DATINGMETHOD text, NONMEASUREDLOCATION text,
      MEASUREMENTFILE text, STRUCKOFF text, CONSTRUCTION int, SUBCONSTRUCTION int, ORIENTATION text, FORM text, COURNERS text, HEIGHT text, RIM text, BOTTOMRIM text, BOTTOM text, SECTION text, CONDITION text, SPLITTING text, TOOLTRACES text, ASSEMBLY text, MATERIAL text, GRANULARITY text, SURFACE text, JOINTINGMATERIAL text, SORTING text, STRUCTURE text, CONTENTS text, CONSISTENCE text, PACKING text, COLOUR text, COMPOSITION text, JOINTING text, CHALK text, COAL text,
      PEBBELS text, BRICKFRAG text, BRICK text, WOOD text, CLAY text, BURNT_CLAY text, DAUB text, GRAVEL text, SOOT text, ASHES text, ANIMALBONES text, FISHBONES text, MACHINE text, SHOVEL text, HOETABLE text, TROWEL text, SIEVE text, PREPARATION text, CONTAMINATION text, DROUGHT text, RAIN text, FROST text, WATERSIEVE text, RECORDEDBY text, VERIFIED text, OBSERVATIONS text, CONTACT_BELOW text, SIDE text, LIMITS text, MAXHEIGHT text,
      DETAILS text, TAQ text, TPQ text, STRATATOP text, STRATABOTTOM text, SAND text, LIME text, PREV_FUNCTION text, DATEEDITED datetime, BLAZINGCOLOR text, FILLING text, TIERS text, TIER_DEPTH text, OBJECTID int, BELONGSTOID int, CONST_PHASE text, DEST_PHASE text, AREA double, SILT text, ORGANIC_MATTER text, IDX int, NOTES text, DIAMETER text, ROCKS text, HUMUS text, BURNT_BONE text, UNBURNT_BONE text, FIRE_CRACKED_ROCK text, BURNT_STONE text, PART text,
      DATING_MARGINOFERROR text, BOULDERS text, CONTACT_ABOVE text, INNER_LENGTH text, INNER_WIDTH text, INNER_HEIGHT text, SECTIONS text, EXAMINATION text, FRAGMENTS text, THICKNESS text
CSV (reader CSV2_19)
    attributes: TYPENR uint32, VIEWTYPE uint32, ASCKONF uint32, MAP varchar(10), CATEGORYCODE varchar(3), CATEGORY varchar(12), CLASS varchar(28), TYPENAME varchar(30), CODE varchar(3), LEVELNO uint32, COLOR uint32, WEIGHT uint32, STYLE uint32, FILL uint32, ELEMENT_TYPE uint32, CLOSED uint32, PATTERN_TYPE int32, PATTERN_CELLNAME varchar(5), ANGLE real32, DIST real32, XANGLE real32, XDIST real32, SCALE_PATTERN real32, TEXT uint32, TEXT_LEVEL uint32, TEXT_SIZE real32, TEXT_FONT uint32, TAG uint32, PLACECELLROTATE uint32, PLACECELLSCALE uint32,
      S1 varchar(16), S2 varchar(12), S3 varchar(5), S4 varchar(7), S5 varchar(6), S6 varchar(1), CONT_CLASS varchar(1), SYMBOLSIZE uint32, SYMBOLTYPE uint32
    -> Table1020606 (writer OGCGEOPACKAGE_1)
Table1020606 (writer OGCGEOPACKAGE_1)
    attributes: TYPENR int, VIEWTYPE int, ASCKONF int, MAP text, CATEGORYCODE text, CATEGORY text, CLASS text, TYPENAME text, CODE text, LEVELNO int, COLOR int, WEIGHT int, STYLE int, FILL int, ELEMENT_TYPE int, CLOSED int, PATTERN_TYPE mediumint, PATTERN_CELLNAME text, ANGLE float, DIST float, XANGLE float, XDIST float, SCALE_PATTERN float, TEXT int, TEXT_LEVEL int, TEXT_SIZE float, TEXT_FONT int, TAG int, PLACECELLROTATE int, PLACECELLSCALE int,
      S1 text, S2 text, S3 text, S4 text, S5 text, S6 text, CONT_CLASS text, SYMBOLSIZE int, SYMBOLTYPE int
CSV (reader CSV2_20)
    attributes: OBJECTTYPE uint32, SPECFIELD uint32, DEFDEFINITION varchar(16)
    -> Table1020607 (writer OGCGEOPACKAGE_1)
Table1020607 (writer OGCGEOPACKAGE_1)
    attributes: OBJECTTYPE int, SPECFIELD int, DEFDEFINITION text
CSV (reader CSV2_21)
    attributes: OBJECTTYPE uint32, PART varchar(20), DEFAULT_VALUE varchar(2)
    -> Table1020608 (writer OGCGEOPACKAGE_1)
Table1020608 (writer OGCGEOPACKAGE_1)
    attributes: OBJECTTYPE int, PART text, DEFAULT_VALUE text
CSV (reader CSV2_22)
    attributes: PATTERN_TYPE int32, PTYPE varchar(14)
    -> Table1020609 (writer OGCGEOPACKAGE_1)
Table1020609 (writer OGCGEOPACKAGE_1)
    attributes: PATTERN_TYPE mediumint, PTYPE text
CSV (reader CSV2_23)
    attributes: OBJECTTYPE uint32, PROCESS varchar(16), DEFAULT_VALUE varchar(2)
    -> Table1020610 (writer OGCGEOPACKAGE_1)
Table1020610 (writer OGCGEOPACKAGE_1)
    attributes: OBJECTTYPE int, PROCESS text, DEFAULT_VALUE text
CSV (reader CSV2_24)
    attributes: PROJECT uint32, OFFICALDESIGNATION varchar(1), PROJECTNAME varchar(1), CLIENT varchar(1), PREMISES varchar(1), PARISH varchar(1), MONUMENT varchar(1), MUNICIPALITY varchar(1), COUNTY varchar(1), PROVINCE varchar(1), BASEMAP varchar(1), PROJECTMANAGER varchar(1), PARTICIPANTS varchar(1), TYPEOFPROJECT varchar(18), STARTOFPROJECT varchar(1), ENDOFPROJECT varchar(1), MANHOURS varchar(1), MACHINEHOURS varchar(1), AREAOFINVEST varchar(1), COORDINATESYST varchar(12), HEIGHTSYST varchar(1), MASL varchar(1), R1 uint32, R2 uint32, R3 uint32, R4 uint32, R5 uint32, R6 uint32, R7 uint32, R8 uint32,
      R9 uint32, R10 varchar(1), DOCMETHOD uint32, STATE uint32, EASTING_MAX x_coordinate, EASTING_MIN real32, NORTHING_MIN y_coordinate, NORTHING_MAX real64, R13 varchar(1)
    -> Table1020611 (writer OGCGEOPACKAGE_1)
Table1020611 (writer OGCGEOPACKAGE_1)
    attributes: PROJECT int, OFFICALDESIGNATION text, PROJECTNAME text, CLIENT text, PREMISES text, PARISH text, MONUMENT text, MUNICIPALITY text, COUNTY text, PROVINCE text, BASEMAP text, PROJECTMANAGER text, PARTICIPANTS text, TYPEOFPROJECT text, STARTOFPROJECT text, ENDOFPROJECT text, MANHOURS text, MACHINEHOURS text, AREAOFINVEST text, COORDINATESYST text, HEIGHTSYST text, MASL text, R1 int, R2 int, R3 int, R4 int, R5 int, R6 int, R7 int, R8 int,
      R9 int, R10 text, DOCMETHOD int, STATE int, EASTING_MAX double, EASTING_MIN float, NORTHING_MIN double, NORTHING_MAX double, R13 text
CSV (reader CSV2_25)
    attributes: PROJECT uint32, LOGINNAME varchar(5)
    -> Table1020612 (writer OGCGEOPACKAGE_1)
Table1020612 (writer OGCGEOPACKAGE_1)
    attributes: PROJECT int, LOGINNAME text
CSV (reader CSV2_26)
    attributes: PROJECT string, TASKNUM string, TASKNAME string, STARTOFTASK string, ENDOFTASK string, TASKSTATE string, NEXTTASK string, RESPONSIBLE string
    -> Table1020613 (writer OGCGEOPACKAGE_1)
Table1020613 (writer OGCGEOPACKAGE_1)
    attributes: PROJECT text, TASKNUM text, TASKNAME text, STARTOFTASK text, ENDOFTASK text, TASKSTATE text, NEXTTASK text, RESPONSIBLE text
CSV (reader CSV2_27)
    attributes: INVESTIGATIONTYPE varchar(20), DEFAULT_VALUE varchar(2)
    -> Table1020614 (writer OGCGEOPACKAGE_1)
Table1020614 (writer OGCGEOPACKAGE_1)
    attributes: INVESTIGATIONTYPE text, DEFAULT_VALUE text
CSV (reader CSV2_28)
    attributes: PROVICE varchar(14), DEFAULT_VALUE varchar(2)
    -> Table1020615 (writer OGCGEOPACKAGE_1)
Table1020615 (writer OGCGEOPACKAGE_1)
    attributes: PROVICE text, DEFAULT_VALUE text
CSV (reader CSV2_29)
    attributes: NAME, varchar(66), CONTENTS varchar(27)
    -> Table1020616 (writer OGCGEOPACKAGE_1)
Table1020616 (writer OGCGEOPACKAGE_1)
    attributes: NAME, text, CONTENTS text
CSV (reader CSV2_30)
    attributes: PROJECT string, CATEGORY string, OBJECTNO string, SUBOBJECT string, RTYPE string, COBJECTNO string, CSUBOBJECT string
    -> Table1020617 (writer OGCGEOPACKAGE_1)
Table1020617 (writer OGCGEOPACKAGE_1)
    attributes: PROJECT text, CATEGORY text, OBJECTNO text, SUBOBJECT text, RTYPE text, COBJECTNO text, CSUBOBJECT text
CSV (reader CSV2_31)
    attributes: OBJECTTYPE uint32, SHAPE varchar(25), DEFAULT_VALUE varchar(2)
    -> Table1020618 (writer OGCGEOPACKAGE_1)
Table1020618 (writer OGCGEOPACKAGE_1)
    attributes: OBJECTTYPE int, SHAPE text, DEFAULT_VALUE text
CSV (reader CSV2_32)
    attributes: OBJECTTYPE uint32, SPECFIELD uint32, DEFDEFINITION varchar(16)
    -> Table1020619 (writer OGCGEOPACKAGE_1)
Table1020619 (writer OGCGEOPACKAGE_1)
    attributes: OBJECTTYPE int, SPECFIELD int, DEFDEFINITION text
CSV (reader CSV2_33)
    attributes: LOGINNAME varchar(17), FULLNAME varchar(19), ACCESSLEVEL uint32
    -> Table1020620 (writer OGCGEOPACKAGE_1)
Table1020620 (writer OGCGEOPACKAGE_1)
    attributes: LOGINNAME text, FULLNAME text, ACCESSLEVEL int
CSV (reader CSV2_34)
    attributes: PROJECT string, STRATA string, TAQ string, TPQ string
    -> Table1020621 (writer OGCGEOPACKAGE_1)
Table1020621 (writer OGCGEOPACKAGE_1)
    attributes: PROJECT text, STRATA text, TAQ text, TPQ text
CSV (reader CSV2_35)
    attributes: DB_VERSION uint32
    -> Table1020622 (writer OGCGEOPACKAGE_1)
Table1020622 (writer OGCGEOPACKAGE_1)
    attributes: DB_VERSION int
CSV (reader CSV2_36)
    attributes: OBJECTTYPE uint32, TECHNIQUE varchar(19), DEFAULT_VALUE varchar(2)
    -> Table1020623 (writer OGCGEOPACKAGE_1)
Table1020623 (writer OGCGEOPACKAGE_1)
    attributes: OBJECTTYPE int, TECHNIQUE text, DEFAULT_VALUE text
CSV (reader CSV2_37)
    attributes: OBJECTTYPE uint32, WEARMARKS varchar(9), DEFAULT_VALUE boolean
    -> Table1020624 (writer OGCGEOPACKAGE_1)
Table1020624 (writer OGCGEOPACKAGE_1)
    attributes: OBJECTTYPE int, WEARMARKS text, DEFAULT_VALUE boolean
CSV (reader CSV2_2)
    attributes: PRECNAME varchar(9), RECORDNINGMETHOD varchar(13), PRECDEFINITION varchar(8), DEFAULT_VALUE varchar(2)
    -> Table1 (writer OGCGEOPACKAGE_1)
Table1 (writer OGCGEOPACKAGE_1)
    attributes: PRECNAME text, RECORDNINGMETHOD text, PRECDEFINITION text, DEFAULT_VALUE text
CSV (reader CSV2_1)
    attributes: OBJECTTYPE uint32, CLASSDEFINITION varchar(34), COMMONTERM varchar(23), DEFAULT_VALUE varchar(2)
    -> Table101 (writer OGCGEOPACKAGE_1)
Table101 (writer OGCGEOPACKAGE_1)
    attributes: OBJECTTYPE int, CLASSDEFINITION text, COMMONTERM text, DEFAULT_VALUE text

Bookmark: fixfix geom
Note: CSV: OBJDATA [CSV2] / geometrier
CSV (reader CSV2_12)
    attributes: SEQNO uint32, X x_coordinate, Y y_coordinate, Z z_coordinate, OBJECTID uint32
    -> VertexCreator
VertexCreator
    MEASURE_TYPE = Continuous
    MODE_NAME = Replace with Point
    XVAL = @Value(X)
    YVAL = @Value(Y)
    ZVAL = @Value(Z)
    -> Aggregator
    -> LineBuilder
Aggregator
    ACCUM_ATTRS_NAME = Drop Incoming Attributes
    AGGREGATE_TYPE = Homogeneous Collection (If Possible)
    COUNT_ATTR = num_of_points
    GROUP_BY = OBJECTID
    MODE = Geometry - Assemble One Level
    SEP = ,
    AGGREGATE -> FeatureMerger [SUPPLIER]
LineBuilder
    ACCUM_INPUT_ATTRS = Use Attributes From One Feature
    GROUP_BY = OBJECTID
    REMOVE_DUPLICATES = No
    POINT -> OBJDATA (writer OGCGEOPACKAGE_1)
    LINE -> FeatureMerger [REQUESTOR]
    POLYGON -> OBJDATA (writer OGCGEOPACKAGE_1)
FeatureMerger
    ATTR_ACCUM_MODE = Merge Supplier
    ATTR_CONFLICT_RES = Use Requestor
    IGNORE_NULLS = No
    JOIN_KEYS = @Value(OBJECTID) @Value(OBJECTID) AUTO
    MERGE_TYPE = Attributes Only
    PROCESS_DUPS = NO
    REJECT_NULL_MISSING_KEYS = No
    SUPPLIERS_FIRST = No
    MERGED -> TestFilter
Note: om fler än 2 vertex
TestFilter
    DEFAULT_VALUE = <UNFILTERED>
    PASSED_TEST_GROUP_OUTPUT = FIRST
    TEST_LIST = "BOOL_OP,OR,COMPOSITE_TEST,""""""1"""""",TEST_CLAUSE,TEST @Value(num_of_points) > 2",polygon
    polygon -> LineCloser
    <UNFILTERED> -> LineCloser
LineCloser
    CONNECT_Z_MODE = First Wins
    AREA -> OBJDATA (writer OGCGEOPACKAGE_1)
OBJDATA (writer OGCGEOPACKAGE_1)
    attributes: SEQNO int, X double, Y double, Z double, OBJECTID int, num_of_points int
