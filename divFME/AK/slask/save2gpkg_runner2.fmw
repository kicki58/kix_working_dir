FME workspace save2gpkg_runner2.fmw

Parameters:
- SourceDataset_PATH = C:\Github\kix\SiteWorks-Py\result   # INCLUDE_WEB_BROWSER Source Folder and File Pathnames Folder

Readers:
- PATH_1: PATH from $(SourceDataset_PATH)

PATH (reader PATH_1)
    attributes: path_unix buffer, path_windows buffer, path_rootname buffer, path_filename buffer, path_extension buffer, path_directory_unix buffer, path_directory_windows buffer, path_type char(10)
    -> AttributeManager
AttributeManager
    ATTR_TABLE:
      SET_TO path_to_csv = @Value(path_windows)\csv
      SET_TO gpkg_file =  @Value(path_directory_windows)@Value(path_filename).gpkg
      SET_TO path_to_csv2 = ..\..\SiteWorks-Py\result
      SET_TO gpkg_file2 = ..\..\SiteWorks-Py\gpkg\@Value(path_filename).gpkg
    -> WorkspaceRunner
WorkspaceRunner
    BLOCKING = Yes
    WORKSPACE_FILE = $(FME_MF_DIR)save2gpkg2.fmw
    WORKSPACE_PARAMETERS = db_name,@Value(path_filename),DestDataset_OGCGEOPACKAGE,C:\Github\kix\SiteWorks-Py\gpkg\result\@Value(path_filename).gpkg,SourceDataset_PATH,C:\Github\kix\SiteWorks-Py\result,SourceDataset_CSV2_43,@Value(path_windows)\csv\OBJDATA.csv,SourceDataset_CSV2_65,@Value(path_windows)\csv\ACCURACY.csv,SourceDataset_CSV2_49,@Value(path_windows)\csv\ARCHIVE.csv,SourceDataset_CSV2_41,@Value(path_windows)\csv\COLOURDEF.csv,SourceDataset_CSV2,@Value(path_windows)\csv\CLASSDEF.csv,SourceDataset_CSV2_57,@Value(path_windows)\csv\COUNTY.csv,SourceDataset_CSV2_73,@Value(path_windows)\csv\DATINGMETHODS.csv,SourceDataset_CSV2_45,@Value(path_windows)\csv\DATINGPERIODS.csv,SourceDataset_CSV2_53,@Value(path_windows)\csv\DECORDEF.csv,SourceDataset_CSV2_61,@Value(path_windows)\csv\DEFDEF.csv,SourceDataset_CSV2_69,@Value(path_windows)\csv\ELMTYPE.csv,SourceDataset_CSV2_39,@Value(path_windows)\csv\LAYERS.csv,SourceDataset_CSV2_47,@Value(path_windows)\csv\MATDEF.csv,SourceDataset_CSV2_51,@Value(path_windows)\csv\MTYPES.csv,SourceDataset_CSV2_55,@Value(path_windows)\csv\MUNICIPALITY.csv,SourceDataset_CSV2_59,@Value(path_windows)\csv\OBJ.csv,SourceDataset_CSV2_63,@Value(path_windows)\csv\OBJDETAILS.csv,SourceDataset_CSV2_67,@Value(path_windows)\csv\OBJECTS.csv,SourceDataset_CSV2_71,@Value(path_windows)\csv\OBJTYP.csv,SourceDataset_CSV2_38,@Value(path_windows)\csv\OBJTYPPROJ.csv,SourceDataset_CSV2_40,@Value(path_windows)\csv\PARTDEF.csv,SourceDataset_CSV2_42,@Value(path_windows)\csv\PATTYP.csv,SourceDataset_CSV2_44,@Value(path_windows)\csv\PROCESSDEF.csv,SourceDataset_CSV2_46,@Value(path_windows)\csv\PROJECT.csv,SourceDataset_CSV2_48,@Value(path_windows)\csv\PROJSTAFF.csv,SourceDataset_CSV2_50,@Value(path_windows)\csv\PROJTASK.csv,SourceDataset_CSV2_52,@Value(path_windows)\csv\PROJTYPE.csv,SourceDataset_CSV2_54,@Value(path_windows)\csv\PROVINCE.csv,SourceDataset_CSV2_56,@Value(path_windows)\csv\QUERIES.csv,SourceDataset_CSV2_58,@Value(path_windows)\csv\RELATIONS.csv,SourceDataset_CSV2_60,@Value(path_windows)\csv\SHAPEDEF.csv,SourceDataset_CSV2_62,@Value(path_windows)\csv\SPECREGDEF.csv,SourceDataset_CSV2_64,@Value(path_windows)\csv\STAFF.csv,SourceDataset_CSV2_66,@Value(path_windows)\csv\STRATA.csv,SourceDataset_CSV2_68,@Value(path_windows)\csv\SYSDATA.csv,SourceDataset_CSV2_70,@Value(path_windows)\csv\TECHNIQUEDEF.csv,SourceDataset_CSV2_72,@Value(path_windows)\csv\WEARDEF.csv
