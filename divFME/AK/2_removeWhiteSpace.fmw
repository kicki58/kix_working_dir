FME workspace 2_removeWhiteSpace.fmw

Parameters:
- SourceDataset_PATH = C:\Github\kix\SiteWorks-Py\result   # INCLUDE_WEB_BROWSER Source Folder and File Pathnames Folder

Readers:
- PATH_1: PATH from $(SourceDataset_PATH)

PATH (reader PATH_1)
    attributes: path_unix buffer, path_windows buffer, path_rootname buffer, path_filename buffer, path_extension buffer, path_directory_unix buffer, path_directory_windows buffer, path_type char(10)
    -> AttributeManager
AttributeManager
    ATTR_TABLE:
      SET_TO new_filename (varchar(200)) = "@ReplaceRegularExpression(@Value(path_filename), ,_,caseSensitive=TRUE)"
      SET_TO old_filename (varchar(200)) = "@Value(path_windows)"
    -> SystemCaller
Note: create folders if not exist / copy gpkg fil
SystemCaller
    CMD = ren @Value(old_filename) @Value(new_filename)
