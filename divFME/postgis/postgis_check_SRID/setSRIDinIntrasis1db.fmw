FME workspace setSRIDinIntrasis1db.fmw

Parameters:
- HOST_POSTGISserver = localhost   # Server
- USER_NAME_POSTGIS = postgres   # Username
- koordsyscode = 4267   # coordsys epsg code
- PORT = 5432   # Port
- databas = MHM6820

Creator
    GEOMTYPE = Geometry Object
    NUM = 1
    CREATED -> AttributeManager
AttributeManager
    ATTR_TABLE:
      SET_TO databas = $(databas)
      SET_TO koordsys = $(koordsyscode)
    -> SQLExecutor [INITIATOR]
Note: SQLExecutor
SQLExecutor
    COMBINE_ATTRS = Result Attributes Only
    COMBINE_GEOM = Initiator Geometry Only
    DATASET = @Value(databas)
    FORMAT = POSTGRES
    OUTPUT_FEATURES_DISPLAY = Schema and Data Features
    POSTGRES_CREATE_FEATURE_TABLES_FROM_DATA = Yes
    POSTGRES_HOST = $(HOST_POSTGISserver)
    POSTGRES_PORT = $(PORT)
    POSTGRES_QUERY_FEATURE_TYPES_FOR_MERGE_FILTERS = Yes
    POSTGRES_READ_TIME_WITH_TIMEZONE = Yes
    POSTGRES_SCHEMAS_FOR_TABLE_LISTING = public
    POSTGRES_SSLMODE = prefer
    POSTGRES_USER_NAME = $(USER_NAME_POSTGIS)
    SQL_STATEMENT:
      FME_SQL_DELIMITER ;
      update  "AttributeValue"  SET "Value"='@Value(koordsys)'
      where "AttributeValueId"= (
      Select av."AttributeValueId"
      from  "SysDefs" sd,  "Attribute" a, "Object" o , "AttributeValue" av
      where
      	sd."SystemId" = 489
          And  o."ObjectId" = a."ObjectId"
      	AND a."MetaId" = sd."MetaId"
          AND  a."AttributeId" = av."AttributeId"
      	And o."ClassId" = 4 );
