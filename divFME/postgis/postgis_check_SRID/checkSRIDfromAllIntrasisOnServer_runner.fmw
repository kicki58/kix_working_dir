FME workspace checkSRIDfromAllIntrasisOnServer_runner.fmw

Parameters:
- HOST_POSTGISserver = localhost   # Server
- PORT = 5432   # Port
- USER_NAME_POSTGIS = postgres   # Username
- DestDataset_CSV2 = C:\ny_slask   # Destination CSV (Comma Separated Value) Folder

Readers:
- POSTGRES_1: POSTGRES from postgres

pg_database (reader POSTGRES_1)
    attributes: oid oid,Unique, datname text,Unique, datdba oid, encoding int4, datcollate text, datctype text, datistemplate bool, datallowconn bool, datconnlimit int4, datlastsysoid oid, datfrozenxid text, datminmxid text, dattablespace oid, datacl text
    -> AttributeManager
AttributeManager
    ATTR_TABLE = RENAME_SET_VALUE datname > intrasisarchive
    -> WorkspaceRunner
WorkspaceRunner
    BLOCKING = Yes
    WORKSPACE_FILE = $(FME_MF_DIR)checkSRIDfromIntrasis.fmw
    WORKSPACE_PARAMETERS = SourceDataset_POSTGIS_2,@Value(intrasisarchive),HOST_POSTGISserver,$(HOST_POSTGISserver),USER_NAME_POSTGIS,$(USER_NAME_POSTGIS),PORT,$(PORT),DestDataset_CSV2,$(DestDataset_CSV2)
