FME workspace removeDBfromServerFrSQL.fmw
Title: SAUimportIntrasis
Description: En import av SAU's databaser.
Vad som krävs
C:\Intrasis\backup_files
Backupfiler med vissa namn ändrade (de som har _ innan datumet i slutet)
pgpass.conf - med lösen för den dbhanteraren som man går mot
i katalogen C:\Users\krima354\AppData\Roaming\postgresql

Parameters:
- server = localhost   # Server
- port = 5433   # Port
- user = postgres   # User
- PASSWORD =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   # Password

SQLCreator
    DATASET = postgres@localhost
    EXPOSED_ATTRIBUTE_LIST = datname
    FORMAT = POSTGRES
    OUTPUT_FEATURES_DISPLAY = Schema and Data Features
    POSTGRES_CREATE_FEATURE_TABLES_FROM_DATA = Yes
    POSTGRES_NAMED_CONNECTION = postgres@localhost
    POSTGRES_QUERY_FEATURE_TYPES_FOR_MERGE_FILTERS = Yes
    POSTGRES_READ_TIME_WITH_TIMEZONE = Yes
    SQL_STATEMENT = SELECT datname FROM pg_database
    RESULT -> TestFilter_2
TestFilter_2
    DEFAULT_VALUE = <UNFILTERED>
    PASSED_TEST_GROUP_OUTPUT = FIRST
    TEST_LIST:
      "BOOL_OP,OR,COMPOSITE_TEST,""""""1 OR 2 OR 3 OR 4 OR 5 OR 6 OR 7 OR 8 OR 9 OR 10"""""",TEST_CLAUSE,TEST @Value(datname) = postgis20
      TEST @Value(datname) = postgis_db
      TEST @Value(datname) = template0
      TEST @Value(datname) = postgres
      TEST @Value(datname) = urdar_template
      TEST @Value(datname) = dap_data
      TEST @Value(datname) = template1
      TEST @Value(datname) = template_postgis_20
      TEST @Value(datname) = intrasislicense
      TEST @Value(datname) = jens",ej_intrasis_db
    <UNFILTERED> -> AttributeManager_2
AttributeManager_2
    ATTR_TABLE = SET_TO db_name = @Value(datname)
    -> SystemCaller
SystemCaller [off]
    ATTR = hejda
    CMD = ""C:/Program Files/PostgreSQL/11/bin/dropdb.exe" -h $(server)  -p $(port) -U $(user)  -w  @Value(db_name)"
