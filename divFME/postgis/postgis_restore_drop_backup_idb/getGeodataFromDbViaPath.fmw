FME workspace getGeodataFromDbViaPath.fmw
Title: SAUimportIntrasis
Description: En import av SAU's databaser.
Vad som krävs
C:\Intrasis\backup_files
Backupfiler med vissa namn ändrade (de som har _ innan datumet i slutet)
pgpass.conf - med lösen för den dbhanteraren som man går mot
i katalogen C:\Users\krima354\AppData\Roaming\postgresql

Parameters:
- SourceDataset_PATH = C:\Users\krima354\Work Folders\Documents\kicki_arbetsfiler\urdar_arbetsfiler\utanfor3006_ses_over\20230918   # INCLUDE_WEB_BROWSER Source Folder and File Pathnames Folder
- num2remove = 0   # numChar2remove
- server = localhost   # Server
- port = 5432   # Port
- user = postgres   # User
- PASSWORD =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   # Password
- SourceDataset_OGCGEOPACKAGE = C:\Users\krima354\Work Folders\Documents\kicki_arbetsfiler\urdar_arbetsfiler\alla40utanfor20230918.gpkg   # GeoPackage File
- DestDataset_OGCGEOPACKAGE = C:\Users\krima354\Work Folders\Documents\kicki_arbetsfiler\urdar_arbetsfiler\alla39utanforFranLocalhost.gpkg   # GeoPackage File

Readers:
- PATH_1: PATH from $(SourceDataset_PATH)
- OGCGEOPACKAGE_1: OGCGEOPACKAGE from $(SourceDataset_OGCGEOPACKAGE) in EPSG:3006

Writers:
- OGCGEOPACKAGE_2: OGCGEOPACKAGE to $(DestDataset_OGCGEOPACKAGE) in EPSG:3006

PATH (reader PATH_1)
    attributes: path_unix buffer, path_windows buffer, path_rootname buffer, path_filename buffer, path_extension buffer, path_directory_unix buffer, path_directory_windows buffer, path_type char(10)
    -> SQLExecutor [INITIATOR]
SQLExecutor
    COMBINE_ATTRS = Result Attributes Only
    COMBINE_GEOM = Result Geometry Only
    COORDSYS = EPSG:3006
    DATASET = @Value(path_rootname)
    EXPOSED_ATTRIBUTE_LIST = idb
    FORMAT = POSTGIS
    OUTPUT_FEATURES_DISPLAY = Schema and Data Features
    POSTGIS_CREATE_FEATURE_TABLES_FROM_DATA = Yes
    POSTGIS_DISABLE_COLLECTION_SPLITTING = yes
    POSTGIS_HOST = $(server)
    POSTGIS_PASSWORD = $(PASSWORD)
    POSTGIS_PORT = 5432
    POSTGIS_QUERY_FEATURE_TYPES_FOR_MERGE_FILTERS = Yes
    POSTGIS_READ_TIME_WITH_TIMEZONE = Yes
    POSTGIS_SCHEMAS_FOR_TABLE_LISTING = public
    POSTGIS_SSLMODE = prefer
    POSTGIS_USER_NAME = $(user)
    POSTGIS_USE_TRUE_POSTGIS_TYPES = yes
    SQL_STATEMENT = select "ObjectId" ,"MetaId","SymbolId", the_geom, '@Value(path_rootname)' as idb from "GeoObject"
    RESULT -> Aggregator
Aggregator
    ACCUM_ATTRS_NAME = Drop Incoming Attributes
    AGGREGATE_TYPE = Homogeneous Collection (If Possible)
    GROUP_BY = idb
    MODE = Geometry - Assemble One Level
    SEP = ,
    AGGREGATE -> alla39 (writer OGCGEOPACKAGE_2)
alla39 (writer OGCGEOPACKAGE_2)
    attributes: idb text
alla40 (reader OGCGEOPACKAGE_1)
    attributes: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
