FME workspace 1_export_from_MSSQL2 (backup) (backup) (backup) (backup).fmw

Parameters:
- SourceDataset_SHAPEFILE = ""C:\Users\krima354\Downloads\Backup_FILER\Backup_FILER\IntrasisData\MK7634\geodata\Polygon.shp" "C:\Users\krima354\Downloads\Backup_FILER\Backup_FILER\IntrasisData\MK7634\geodata\LPolygon.shp" "C:\Users\krima354\Downloads\Backup_FILER\Backup_FILER\IntrasisData\MK7634\geodata\Line.shp" "C:\Users\krima354\Downloads\Backup_FILER\Backup_FILER\IntrasisData\MK7634\geodata\ILine.shp" "C:\Users\krima354\Downloads\Backup_FILER\Backup_FILER\IntrasisData\MK7634\geodata\IMultiP.shp" "C:\Users\krima354\Downloads\Backup_FILER\Backup_FILER\IntrasisData\MK7634\geodata\IPoint.shp" "C:\Users\krima354\Downloads\Backup_FILER\Backup_FILER\IntrasisData\MK7634\geodata\IPolygon.shp" "C:\Users\krima354\Downloads\Backup_FILER\Backup_FILER\IntrasisData\MK7634\geodata\LLine.shp" "C:\Users\krima354\Downloads\Backup_FILER\Backup_FILER\IntrasisData\MK7634\geodata\LMultiP.shp" "C:\Users\krima354\Downloads\Backup_FILER\Backup_FILER\IntrasisData\MK7634\geodata\LPoint.shp" "C:\Users\krima354\Downloads\Backup_FILER\Backup_FILER\IntrasisData\MK7634\geodata\MultiP.shp" "C:\Users\krima354\Downloads\Backup_FILER\Backup_FILER\IntrasisData\MK7634\geodata\Point.shp""   # Source Esri Shapefile(s)
- DestDataset_SQLITE3 = C:\ny_slask\mm_2\MK7634_test4.gpkg   # Dest SQLlite/gpkg
- SourceDataset_SQLITE3 = C:\ny_slask\mm_2\mall.gpkg   # Mall reader SQLite/gpkg
- SourceDataset_MSSQL_ADO_1 = MK7634   # Database

Readers:
- MSSQL_ADO_1: MSSQL_ADO from $(SourceDataset_MSSQL_ADO_1)
- SHAPEFILE_1: SHAPEFILE from $(SourceDataset_SHAPEFILE)
- SQLITE3_2: SQLITE3 from $(SourceDataset_SQLITE3)

Writers:
- OGCGEOPACKAGE_1: OGCGEOPACKAGE to $(DestDataset_SQLITE3)
- SQLITE3_1: SQLITE3 to $(DestDataset_SQLITE3)

GeoObjectDef (reader MSSQL_ADO_1)
    attributes: MetaId integer, Code char(2), Type char(20)
Symbol (reader MSSQL_ADO_1)
    attributes: SymbolId identity, MetaId integer, SymbolIndex smallint, Type char(30), Context char(30), Font char(30), IconReference char(50), SymbolSize integer
AttributeFilter
    ATTR_NAME = Class
    ATTR_VALUES = <Empty>,<Missing>,<Null>,<Unfiltered>,GeoObjekt,Mätning,System,Personal
    <UNFILTERED> -> objects (writer OGCGEOPACKAGE_1)
    <UNFILTERED> -> FeatureMerger_13 [SUPPLIER]
objects (writer OGCGEOPACKAGE_1)
    attributes: IntrasisId int, Name text, Class text, SubClass text, Color int, geometry_count int, attributes text, object_id int,PrimaryKey
ObjectDef (reader MSSQL_ADO_1)
    attributes: MetaId integer, Code char(10), Id integer, Color integer, CanAddAttribute smallint
layer_styles (writer OGCGEOPACKAGE_1) [off]
    attributes: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

Bookmark: objekt
ClassDef (reader MSSQL_ADO_1)
    attributes: MetaId integer, CanAddSubclass smallint, SpecialRegIsActive smallint, InfoGroupDefId integer, DefaultAttributeDefId integer
    -> FeatureMerger_2 [REQUESTOR]
Definition (reader MSSQL_ADO_1)
    attributes: MetaId identity, VersionReferenceId integer, Name char(50), Description varchar(100), ToolTip varchar(50), Help text, IsVisible smallint, ExternalId integer
    -> FeatureMerger_2 [SUPPLIER]
    -> FeatureMerger_3 [SUPPLIER]
    -> FeatureMerger_10 [SUPPLIER]
FeatureMerger_2
    ATTR_ACCUM_MODE = Merge Supplier
    ATTR_CONFLICT_RES_LOOKUP = REQUESTOR_IF_CONFLICT
    IGNORE_NULLS = No
    JOIN_KEYS = @Value(MetaId) @Value(MetaId) AUTO
    MERGE_TYPE = Attributes Only
    PROCESS_DUPS = NO
    REJECT_NULL_MISSING_KEYS = No
    SUPPLIERS_FIRST = No
    ATTR_CONFLICT_RES = Use Requestor
    MERGED -> FeatureMerger_4 [SUPPLIER]
    MERGED -> BulkAttributeRenamer
BulkAttributeRenamer
    ATTRCHOICE_ACTION = NONPROTECTEDFME
    MODE_CHOICE = RENAME
    PATTERN_ACTION_DISP = ADDPREFIX
    REPLACE_STR = class_
    ATTRCHOICE = All Attributes
    -> FeatureMerger_5 [SUPPLIER]
SubClassDef (reader MSSQL_ADO_1)
    attributes: MetaId integer, ClassId integer, IsInUse smallint
    -> FeatureMerger_3 [REQUESTOR]
FeatureMerger_3
    ATTR_ACCUM_MODE = Merge Supplier
    ATTR_CONFLICT_RES_LOOKUP = REQUESTOR_IF_CONFLICT
    IGNORE_NULLS = No
    JOIN_KEYS = @Value(MetaId) @Value(MetaId) AUTO
    MERGE_TYPE = Attributes Only
    PROCESS_DUPS = NO
    REJECT_NULL_MISSING_KEYS = No
    SUPPLIERS_FIRST = No
    ATTR_CONFLICT_RES = Use Requestor
    MERGED -> FeatureMerger_4 [REQUESTOR]
FeatureMerger_4
    ATTR_ACCUM_MODE = Merge Supplier
    ATTR_CONFLICT_RES_LOOKUP = REQUESTOR_IF_CONFLICT
    IGNORE_NULLS = No
    JOIN_KEYS = @Value(ClassId) @Value(MetaId) AUTO
    MERGE_TYPE = Attributes Only
    PROCESS_DUPS = NO
    REJECT_NULL_MISSING_KEYS = No
    SUPPLIERS_FIRST = No
    ATTR_CONFLICT_RES = Use Requestor
    MERGED -> BulkAttributeRenamer_2
BulkAttributeRenamer_2
    ATTRCHOICE_ACTION = NONPROTECTEDFME
    MODE_CHOICE = RENAME
    PATTERN_ACTION_DISP = ADDPREFIX
    REPLACE_STR = subclass_
    ATTRCHOICE = All Attributes
    -> FeatureMerger_6 [SUPPLIER]
GeoObject (reader MSSQL_ADO_1)
    attributes: ObjectId integer, MeasurementJobId integer, MetaId integer, ShapeId identity
    -> FeatureMerger_7 [SUPPLIER]
Object (reader MSSQL_ADO_1)
    attributes: ObjectId identity, ClassId integer, SubClassid integer, Id integer, Name char(50), IsRegistered smallint, SiteId integer
    -> FeatureMerger_5 [REQUESTOR]
FeatureMerger_5
    ATTR_ACCUM_MODE = Merge Supplier
    ATTR_CONFLICT_RES_LOOKUP = REQUESTOR_IF_CONFLICT
    IGNORE_NULLS = No
    JOIN_KEYS = @Value(ClassId) @Value(class_MetaId) AUTO
    MERGE_TYPE = Attributes Only
    PROCESS_DUPS = NO
    REJECT_NULL_MISSING_KEYS = No
    SUPPLIERS_FIRST = No
    ATTR_CONFLICT_RES = Use Requestor
    MERGED -> AttributeManager
AttributeManager
    ATTR_TABLE:
      REMOVE ClassId (int32)
      REMOVE IsRegistered (int16)
      SET_TO SiteId (int32)
      SET_TO ToolTip (varchar(50))
      SET_TO class_MetaId (int32)
      SET_TO class_CanAddSubclass (int16)
      SET_TO class_SpecialRegIsActive (int16)
      SET_TO class_InfoGroupDefId (int32)
      SET_TO class_DefaultAttributeDefId (int32)
      RENAME_SET_VALUE class_Name > Class (char(50))
      REMOVE class_Description (varchar(100))
      REMOVE class_ToolTip (varchar(50))
      REMOVE class_Help (buffer)
      REMOVE class_IsVisible (int16)
    USER_EXPOSED_ATTRIBUTES = ToolTip
    -> FeatureMerger_6 [REQUESTOR]
FeatureMerger_6
    ATTR_ACCUM_MODE = Merge Supplier
    ATTR_CONFLICT_RES_LOOKUP = REQUESTOR_IF_CONFLICT
    IGNORE_NULLS = No
    JOIN_KEYS = @Value(SubClassid) @Value(subclass_MetaId) AUTO
    MERGE_TYPE = Attributes Only
    PROCESS_DUPS = NO
    REJECT_NULL_MISSING_KEYS = No
    SUPPLIERS_FIRST = No
    ATTR_CONFLICT_RES = Use Requestor
    MERGED -> AttributeManager_2
    UNMERGED_REQUESTOR -> AttributeManager_2
AttributeManager_2
    ATTR_TABLE:
      RENAME_SET_VALUE ObjectId > object_id (int32)
      REMOVE SubClassid (int32)
      RENAME_SET_VALUE Id > IntrasisId (int32)
      REMOVE SiteId (int32)
      REMOVE ToolTip (varchar(50))
      REMOVE class_MetaId (int32)
      REMOVE class_CanAddSubclass (int16)
      REMOVE class_SpecialRegIsActive (int16)
      REMOVE class_InfoGroupDefId (int32)
      REMOVE class_DefaultAttributeDefId (int32)
      REMOVE class_VersionReferenceId (int32)
      REMOVE class_ExternalId (int32)
      REMOVE subclass_MetaId (int32)
      REMOVE subclass_ClassId (int32)
      REMOVE subclass_IsInUse (int16)
      REMOVE subclass_VersionReferenceId (int32)
      RENAME_SET_VALUE subclass_Name > SubClass (char(50))
      REMOVE subclass_Description (varchar(100))
      REMOVE subclass_ToolTip (varchar(50))
      REMOVE subclass_Help (buffer)
      REMOVE subclass_IsVisible (int16)
      REMOVE subclass_ExternalId (int32)
      REMOVE subclass_CanAddSubclass (int16)
      REMOVE subclass_SpecialRegIsActive (int16)
      REMOVE subclass_InfoGroupDefId (int32)
      REMOVE subclass_DefaultAttributeDefId (int32)
    -> FeatureMerger_9 [SUPPLIER]
    -> AttributeFilter

Bookmark: shapefiles
ILine (reader SHAPEFILE_1)
    attributes: ShapeID number(15,0), MetaID number(15,0)
    -> Tester
IMultiP (reader SHAPEFILE_1)
    attributes: ShapeID number(15,0), MetaID number(15,0)
    -> Tester
IPoint (reader SHAPEFILE_1)
    attributes: ShapeID number(15,0), MetaID number(15,0)
    -> Tester
IPolygon (reader SHAPEFILE_1)
    attributes: ShapeID number(15,0), MetaID number(15,0)
    -> Tester
Line (reader SHAPEFILE_1)
    attributes: ShapeID number(15,0), MetaID number(15,0)
    -> Tester
LLine (reader SHAPEFILE_1)
    attributes: Date varchar(20), ShapeID number(15,0), MetaID number(15,0)
    -> Tester
LMultiP (reader SHAPEFILE_1)
    attributes: Date varchar(20), ShapeID number(15,0), MetaID number(15,0)
    -> Tester
LPoint (reader SHAPEFILE_1)
    attributes: Date varchar(20), ShapeID number(15,0), MetaID number(15,0)
    -> Tester
LPolygon (reader SHAPEFILE_1)
    attributes: Date varchar(20), ShapeID number(15,0), MetaID number(15,0)
    -> Tester
MultiP (reader SHAPEFILE_1)
    attributes: ShapeID number(15,0), MetaID number(15,0)
    -> Tester
Point (reader SHAPEFILE_1)
    attributes: ShapeID number(15,0), MetaID number(15,0)
    -> Tester
Polygon (reader SHAPEFILE_1)
    attributes: ShapeID number(15,0), MetaID number(15,0)
    -> Tester

Bookmark: features
Tester
    BOOL_OP = OR
    TEST_CLAUSE = TEST 1 = 1
    TEST_MODE = TEST
    PASSED -> FeatureMerger_7 [REQUESTOR]
FeatureMerger_7
    ATTR_ACCUM_MODE = Merge Supplier
    ATTR_CONFLICT_RES_LOOKUP = REQUESTOR_IF_CONFLICT
    CLEANING_TOLERANCE_LOOKUP = AUTO
    CONNECT_Z_MODE_LOOKUP = FIRST_WINS
    GEOM_TYPE_VAL = POLYGONS
    IGNORE_NULLS = No
    JOIN_KEYS = @Value(ShapeID) @Value(ShapeId) AUTO
    MERGE_TYPE = Attributes and Geometry
    PROCESS_DUPS = YES
    REJECT_NULL_MISSING_KEYS = No
    SUPPLIERS_FIRST = No
    ATTR_CONFLICT_RES = Use Requestor
    CLEANING_TOLERANCE = Automatic
    CONNECT_Z_MODE = First Wins
    GEOM_TYPE = Build Polygons
    MERGED -> GeometryFilter
GeometryFilter
    FILTER_MODE = SIMPLE
    FILTER_MULTI = FILTER_TYPES]"Null Point Line Area"]FME_CONTROLLER_QUERY_FILE]]FME_CONTROLLER_CHOICE]Simple
    Point -> AttributeManager_3
    Curve -> AttributeManager_4
    Curve -> Aggregator_2
    Area -> AttributeManager_5
    Area -> Aggregator
AttributeManager_3
    ATTR_TABLE = SET_TO spatial_type (varchar(5)) = Point
    -> AttributeManager_6
AttributeManager_4
    ATTR_TABLE = SET_TO spatial_type (varchar(8)) = Polyline
    -> AttributeManager_6
AttributeManager_5
    ATTR_TABLE = SET_TO spatial_type (varchar(5)) = Point
    -> AttributeManager_6
AttributeManager_6
    -> FeatureMerger_8 [REQUESTOR]
GeoRel (reader MSSQL_ADO_1)
    attributes: ObjectId integer, GeoObjectId integer
    -> BulkAttributeRenamer_3
BulkAttributeRenamer_3
    ATTRCHOICE_ACTION = NONPROTECTEDFME
    MODE_CHOICE = RENAME
    PATTERN_ACTION_DISP = ADDPREFIX
    REPLACE_STR = GeoRel2_
    ATTRCHOICE = All Attributes
    -> FeatureMerger_8 [SUPPLIER]
FeatureMerger_8
    ATTR_ACCUM_MODE = Prefix Supplier
    CLEANING_TOLERANCE_LOOKUP = AUTO
    CONNECT_Z_MODE_LOOKUP = FIRST_WINS
    GEOM_TYPE_VAL = POLYGONS
    IGNORE_NULLS = No
    JOIN_KEYS = @Value(ObjectId) @Value(GeoRel2_GeoObjectId) AUTO
    LIST_NAME = list
    MERGE_TYPE = Attributes Only
    PROCESS_DUPS = YES
    REJECT_NULL_MISSING_KEYS = No
    SUPPLIERS_FIRST = No
    SUPPLIER_PREFIX = sup
    CLEANING_TOLERANCE = Automatic
    CONNECT_Z_MODE = First Wins
    GEOM_TYPE = Build Polygons
    MERGED -> ListExploder
ListExploder
    ATTR_ACCUM_MODE = Merge List Attributes
    ATTR_CONFLICT_RES_LOOKUP = INCOMING_IF_CONFLICT
    INDEX_ATTR = _element_index
    LIST_ATTR = list{}
    ATTR_CONFLICT_RES = Use List Attribute Values
    ELEMENTS -> AttributeManager_8
AttributeManager_8
    -> FeatureMerger_9 [REQUESTOR]
FeatureMerger_9
    ATTR_ACCUM_MODE = Merge Supplier
    ATTR_CONFLICT_RES_LOOKUP = REQUESTOR_IF_CONFLICT
    CLEANING_TOLERANCE_LOOKUP = AUTO
    CONNECT_Z_MODE_LOOKUP = FIRST_WINS
    GEOM_TYPE_VAL = POLYGONS
    IGNORE_NULLS = No
    JOIN_KEYS = @Value(GeoRel2_ObjectId) @Value(object_id) AUTO
    MERGE_TYPE = Attributes and Geometry
    PROCESS_DUPS = YES
    REJECT_NULL_MISSING_KEYS = No
    SUPPLIERS_FIRST = No
    ATTR_CONFLICT_RES = Use Requestor
    CLEANING_TOLERANCE = Automatic
    CONNECT_Z_MODE = First Wins
    GEOM_TYPE = Build Polygons
    MERGED -> AttributeManager_7
    MERGED -> GeometryFilter_2
Note: R
AttributeManager_7
    ATTR_TABLE:
      SET_TO spatial_type (varchar(5)) = FME_CONDITIONAL:DEFAULT_VALUE'_FME_NO_OP_'BOOL_OP;OR;COMPOSITE_TEST;1;TEST @GeometryType() = fme_polygon'Polygon'BOOL_OP;OR;COMPOSITE_TEST;1;TEST @GeometryType() = fme_line'Polyline'BOOL_OP;OR;COMPOSITE_TEST;1;TEST @GeometryType() = fme_point'Point'BOOL_OP;OR;COMPOSITE_TEST;1;TEST @GeometryType() = fme_multipoint'Multipoint'FME_NUM_CONDITIONS5___
      RENAME_SET_VALUE GeoRel2_ObjectId > object_id (int32)
      RENAME_SET_VALUE GeoRel2_GeoObjectId > GeoObjectId (int32)
      RENAME_SET_DEFAULT ShapeID (number(15,0))
      RENAME_SET_DEFAULT MetaID (number(15,0))
      RENAME_SET_DEFAULT Date (varchar(20))
      RENAME_SET_DEFAULT ObjectId (int32)
      RENAME_SET_DEFAULT MeasurementJobId (int32)
      RENAME_SET_DEFAULT MetaId (int32)
      RENAME_SET_DEFAULT ShapeId (int32)
      RENAME_SET_DEFAULT IntrasisId (int32)
      RENAME_SET_DEFAULT Name (char(50))
      RENAME_SET_DEFAULT Class (char(50))
      RENAME_SET_DEFAULT SubClass (char(50))
      RENAME_SET_DEFAULT supGeoRel2_ObjectId (int32)
      RENAME_SET_DEFAULT supGeoRel2_GeoObjectId (int32)
    USER_EXPOSED_ATTRIBUTES = ShapeID,MetaID,Date,ObjectId,MeasurementJobId,MetaId,ShapeId,spatial_type,GeoRel2_ObjectId,GeoRel2_GeoObjectId,IntrasisId,Name,Class,SubClass
    -> features (writer OGCGEOPACKAGE_1)
Note: VIKET ID SKA ANVÄNDAS?? / symbolID ???
features (writer OGCGEOPACKAGE_1)
    attributes: object_id mediumint, SymbolId mediumint, GeoObjectId mediumint, spatial_type text
GeometryFilter_2 [off]
    FILTER_MODE = SIMPLE
    FILTER_MULTI = FILTER_TYPES]"Null Point Text Line Area Surface Solid Raster PointCloud VoxelGrid"]FME_CONTROLLER_QUERY_FILE]]FME_CONTROLLER_CHOICE]Simple

Bookmark: LÄGG I EGET WS- skapas vyer och lägg till i gpkg-tabellerna
Aggregator [off]
    ACCUM_ATTRS_NAME = Merge Incoming Attributes
    AGGREGATE_TYPE = Homogeneous Collection (If Possible)
    MODE = Geometry - Assemble One Level
    SEP = ,
    AGGREGATE -> SQLExecutor [INITIATOR] [off]
SQLExecutor [off]
    COMBINE_ATTRS = Result Attributes Only
    COMBINE_GEOM = Initiator Geometry Only
    DATASET = $(DestDataset_SQLITE3)
    FORMAT = SQLITE3
    OUTPUT_FEATURES = DATA_ONLY
    SQLITE3_CREATE_FEATURE_TABLES_FROM_DATA = No
    SQLITE3_QUERY_FEATURE_TYPES_FOR_MERGE_FILTERS = Yes
    SQLITE3_SUPPORT_INTERNATIONALIZATION = YES
    SQL_STATEMENT = CREATE VIEW Polygon AS SELECT f.fid, o.IntrasisId, f.object_id, o.Name, o.Class, o.SubClass, f.SymbolId, f.GeoObjectId, f.spatial_type, f.geom FROM features f JOIN objects o ON f.object_id = o.Object_id AND spatial_type = 'Polygon'
Aggregator_2 [off]
    ACCUM_ATTRS_NAME = Merge Incoming Attributes
    AGGREGATE_TYPE = Homogeneous Collection (If Possible)
    MODE = Geometry - Assemble One Level
    SEP = ,
    AGGREGATE -> SQLExecutor_2 [INITIATOR] [off]
SQLExecutor_2 [off]
    COMBINE_ATTRS = Result Attributes Only
    COMBINE_GEOM = Initiator Geometry Only
    DATASET = $(DestDataset_SQLITE3)
    FORMAT = SQLITE3
    OUTPUT_FEATURES = DATA_ONLY
    SQLITE3_CREATE_FEATURE_TABLES_FROM_DATA = No
    SQLITE3_QUERY_FEATURE_TYPES_FOR_MERGE_FILTERS = Yes
    SQLITE3_SUPPORT_INTERNATIONALIZATION = YES
    SQL_STATEMENT = CREATE VIEW Line AS SELECT f.fid, o.IntrasisId, f.object_id, o.Name, o.Class, o.SubClass, f.SymbolId, f.GeoObjectId, f.spatial_type, f.geom FROM features f JOIN objects o ON f.object_id = o.Object_id AND spatial_type = 'Line'

Bookmark: object_relations
ObjectRel (reader MSSQL_ADO_1)
    attributes: ParentId integer, ChildId integer, MetaId integer
    -> FeatureMerger_10 [REQUESTOR]
FeatureMerger_10
    ATTR_ACCUM_MODE = Merge Supplier
    ATTR_CONFLICT_RES_LOOKUP = REQUESTOR_IF_CONFLICT
    IGNORE_NULLS = No
    JOIN_KEYS = @Value(MetaId) @Value(MetaId) AUTO
    MERGE_TYPE = Attributes Only
    PROCESS_DUPS = NO
    REJECT_NULL_MISSING_KEYS = No
    SUPPLIERS_FIRST = No
    ATTR_CONFLICT_RES = Use Requestor
    MERGED -> AttributeManager_9
    MERGED -> FeatureMerger_12 [REQUESTOR]
AttributeManager_9 [off]
    ATTR_TABLE:
      RENAME_SET_VALUE ParentId > base_id (int32)
      RENAME_SET_VALUE ChildId > related_id (int32)
      SET_TO base_text (varchar(200)) = @Substring(@Value(Name),0,@FindRegularExpression(@Value(Name) , / ))
      SET_TO related_text (varchar(200)) = @Substring(@Value(Name),@FindRegularExpression(@Value(Name) ,/ )+1 )
    -> Counter
RelationDef (reader MSSQL_ADO_1)
    attributes: MetaId integer, ParentText char(30), ChildText char(30), RelationType char(10)
    -> FeatureMerger_12 [SUPPLIER]
FeatureMerger_12
    ATTR_ACCUM_MODE = Merge Supplier
    ATTR_CONFLICT_RES_LOOKUP = REQUESTOR_IF_CONFLICT
    IGNORE_NULLS = No
    JOIN_KEYS = @Value(MetaId) @Value(MetaId) AUTO
    MERGE_TYPE = Attributes Only
    PROCESS_DUPS = NO
    REJECT_NULL_MISSING_KEYS = No
    SUPPLIERS_FIRST = No
    ATTR_CONFLICT_RES = Use Requestor
    MERGED -> AttributeManager_11
AttributeManager_11
    ATTR_TABLE:
      RENAME_SET_VALUE ParentText > base_text (char(30))
      RENAME_SET_VALUE ChildText > related_text (char(30))
      RENAME_SET_VALUE ParentId > base_id (int32)
      RENAME_SET_VALUE ChildId > related_id (int32)
      REMOVE MetaId (int32)
      REMOVE VersionReferenceId (int32)
      REMOVE Name (char(50))
      REMOVE Description (varchar(100))
      REMOVE ToolTip (varchar(50))
      REMOVE Help (buffer)
      REMOVE IsVisible (int16)
      REMOVE ExternalId (int32)
    -> Counter
Counter
    CNT_ATTR = id
    DOMAIN = counter
    SCOPE = Global
    START = 1
    -> object_relations (writer OGCGEOPACKAGE_1)
object_relations (writer OGCGEOPACKAGE_1)
    attributes: base_id mediumint, related_id mediumint, base_text text(30), related_text text(30), id int,PrimaryKey

Bookmark: attributes- attributerelations
Attribute (reader MSSQL_ADO_1)
    attributes: AttributeId identity, MetaId integer, ObjectId integer, Label char(50)
    -> FeatureMerger [REQUESTOR]
AttributeValue (reader MSSQL_ADO_1)
    attributes: AttributeId integer, Value varchar(260), Unit varchar(30)
    -> FeatureMerger [SUPPLIER]
FeatureMerger
    ATTR_ACCUM_MODE = Merge Supplier
    ATTR_CONFLICT_RES_LOOKUP = REQUESTOR_IF_CONFLICT
    IGNORE_NULLS = No
    JOIN_KEYS = @Value(AttributeId) @Value(AttributeId) AUTO
    MERGE_TYPE = Attributes Only
    PROCESS_DUPS = NO
    REJECT_NULL_MISSING_KEYS = No
    SUPPLIERS_FIRST = No
    ATTR_CONFLICT_RES = Use Requestor
    MERGED -> FeatureMerger_11 [REQUESTOR]
AttributeDef (reader MSSQL_ADO_1)
    attributes: MetaId integer, Label char(30), MultipleAllowed smallint, FreeValueAllowed smallint, NotNull smallint, DataType char(35), DefaultValue varchar(250), Unit char(20), Length smallint, ControlAttributeId integer
    -> FeatureMerger_11 [SUPPLIER]
FeatureMerger_11
    ATTR_ACCUM_MODE = Merge Supplier
    ATTR_CONFLICT_RES_LOOKUP = REQUESTOR_IF_CONFLICT
    IGNORE_NULLS = No
    JOIN_KEYS = @Value(MetaId) @Value(MetaId) AUTO
    MERGE_TYPE = Attributes Only
    PROCESS_DUPS = NO
    REJECT_NULL_MISSING_KEYS = No
    SUPPLIERS_FIRST = No
    ATTR_CONFLICT_RES = Use Requestor
    MERGED -> FeatureMerger_13 [REQUESTOR]
FeatureMerger_13
    ATTR_ACCUM_MODE = Merge Supplier
    ATTR_CONFLICT_RES_LOOKUP = REQUESTOR_IF_CONFLICT
    IGNORE_NULLS = No
    JOIN_KEYS = @Value(ObjectId) @Value(object_id) AUTO
    MERGE_TYPE = Attributes Only
    PROCESS_DUPS = NO
    REJECT_NULL_MISSING_KEYS = No
    SUPPLIERS_FIRST = No
    ATTR_CONFLICT_RES = Use Requestor
    MERGED -> AttributeManager_10
AttributeManager_10
    ATTR_TABLE:
      RENAME_SET_VALUE Class > class (char(50))
      RENAME_SET_VALUE DataType > data_type (char(35))
      RENAME_SET_VALUE AttributeId > attribute_id (int32)
      RENAME_SET_VALUE Label > attribute_label (char(50))
      RENAME_SET_VALUE Value > attribute_value (varchar(260))
      RENAME_SET_VALUE Unit > attribute_unit (varchar(30))
      REMOVE MetaId (int32)
      REMOVE MultipleAllowed (int16)
      REMOVE FreeValueAllowed (int16)
      REMOVE NotNull (int16)
      REMOVE DefaultValue (varchar(250))
      REMOVE Length (int16)
      REMOVE ControlAttributeId (int32)
      REMOVE IntrasisId (int32)
      REMOVE Name (char(50))
      REMOVE SubClass (char(50))
      REMOVE ObjectId (int32)
    -> attributes (writer OGCGEOPACKAGE_1)
    -> AttributeManager_12
AttributeManager_12
    ATTR_TABLE:
      RENAME_SET_VALUE attribute_id > related_id (int32)
      RENAME_SET_VALUE object_id > base_id (int32)
    -> Counter_2
Counter_2
    CNT_ATTR = id
    DOMAIN = counter
    SCOPE = Global
    START = 1
    -> attribute_relations (writer OGCGEOPACKAGE_1)
attribute_relations (writer OGCGEOPACKAGE_1)
    attributes: related_id mediumint, base_id mediumint, id int,PrimaryKey
attributes (writer OGCGEOPACKAGE_1)
    attributes: object_id int, attribute_label text, attribute_value text, attribute_unit text, class int, data_type text, attribute_id int,PrimaryKey

Bookmark: gpkg extensions
gpkg_extensions (reader SQLITE3_2)
    attributes: table_name text,Unique, column_name text,Unique, extension_name text,Unique, definition text, scope text
    -> Tester_2
Tester_2
    BOOL_OP = OR
    TEST_CLAUSE:
      TEST @Value(table_name) = attribute_relations
      TEST @Value(table_name) = gpkg_metadata
      TEST @Value(table_name) = gpkg_metadata_reference
      TEST @Value(table_name) = gpkgext_relations
      TEST @Value(table_name) = object_relations
    TEST_MODE = TEST
    PASSED -> gpkg_extensions (writer SQLITE3_1)
gpkg_extensions (writer SQLITE3_1)
    attributes: table_name text,Unique, column_name text,Unique, extension_name text,Unique, definition text, scope text
gpkgext_relations (reader SQLITE3_2)
    attributes: id integer, base_table_name text, base_primary_column text, related_table_name text, related_primary_column text, relation_name text, mapping_table_name text,Unique
    -> gpkgext_relations (writer SQLITE3_1)
gpkgext_relations (writer SQLITE3_1)
    attributes: id integer, base_table_name text, base_primary_column text, related_table_name text, related_primary_column text, relation_name text, mapping_table_name text,Unique

Bookmark: METADATA
gpkg_metadata (reader SQLITE3_2)
    attributes: id integer, md_scope text, md_standard_uri text, mime_type text, metadata text
    -> gpkg_metadata (writer SQLITE3_1)
gpkg_metadata (writer SQLITE3_1)
    attributes: id integer, md_scope text, md_standard_uri text, mime_type text, metadata text
