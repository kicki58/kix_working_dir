FME workspace 1_writeFeatures_icke_intrasis.fmw

Parameters:
- SourceDataset_SHAPEFILE = ""K:\jonkoping\JM2004123\geodata\ILine.shp" "K:\jonkoping\JM2004123\geodata\IMultiP.shp" "K:\jonkoping\JM2004123\geodata\IPoint.shp" "K:\jonkoping\JM2004123\geodata\IPolygon.shp" "K:\jonkoping\JM2004123\geodata\Line.shp" "K:\jonkoping\JM2004123\geodata\LLine.shp" "K:\jonkoping\JM2004123\geodata\LMultiP.shp" "K:\jonkoping\JM2004123\geodata\LPoint.shp" "K:\jonkoping\JM2004123\geodata\LPolygon.shp" "K:\jonkoping\JM2004123\geodata\MultiP.shp" "K:\jonkoping\JM2004123\geodata\Point.shp" "K:\jonkoping\JM2004123\geodata\Polygon.shp""   # Source Esri Shapefile(s)
- SourceDataset_MSSQL_ADO = JM2004123   # Database
- DestDataset_OGCGEOPACKAGE_2 = C:\ny_slask\jonkoping\gpkg_export2\not_comverted\dubbelkolla\JM2004123.gpkg   # GeoPackage File
- DestDataset_OGCGEOPACKAGE = C:\ny_slask\mm_2\gpkg\S2004005.gpkg   # GeoPackage File

Readers:
- MSSQL_ADO_1: MSSQL_ADO from $(SourceDataset_MSSQL_ADO)
- SHAPEFILE_1: SHAPEFILE from $(SourceDataset_SHAPEFILE)

Writers:
- OGCGEOPACKAGE_1: OGCGEOPACKAGE to $(DestDataset_OGCGEOPACKAGE_2)

GeoObjectDef (reader MSSQL_ADO_1)
    attributes: MetaId integer, Code char(2), Type char(20)

Bookmark: objekt
ClassDef (reader MSSQL_ADO_1)
    attributes: MetaId integer, CanAddSubclass smallint, SpecialRegIsActive smallint, InfoGroupDefId integer, DefaultAttributeDefId integer
    -> FeatureMerger_2 [REQUESTOR]
SubClassDef (reader MSSQL_ADO_1)
    attributes: MetaId integer, ClassId integer, IsInUse smallint
    -> FeatureMerger_3 [REQUESTOR]
Definition (reader MSSQL_ADO_1)
    attributes: MetaId identity, VersionReferenceId integer, Name char(50), Description varchar(100), ToolTip varchar(50), Help text, IsVisible smallint, ExternalId integer
    -> FeatureMerger_2 [SUPPLIER]
    -> FeatureMerger_3 [SUPPLIER]
FeatureMerger_2
    ATTR_ACCUM_MODE = Merge Supplier
    ATTR_CONFLICT_RES_LOOKUP = REQUESTOR_IF_CONFLICT
    IGNORE_NULLS = No
    JOIN_KEYS = @Value(MetaId) @Value(MetaId) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> FeatureMerger_4 [SUPPLIER]
    MERGED -> BulkAttributeRenamer
BulkAttributeRenamer
    ATTRCHOICE_ACTION = NONPROTECTEDFME
    MODE_CHOICE = RENAME
    PATTERN_ACTION_DISP = ADDPREFIX
    REPLACE_STR = class_
    ATTRCHOICE = All Attributes
    -> FeatureMerger_5 [SUPPLIER]
FeatureMerger_3
    ATTR_ACCUM_MODE = Merge Supplier
    ATTR_CONFLICT_RES_LOOKUP = REQUESTOR_IF_CONFLICT
    IGNORE_NULLS = No
    JOIN_KEYS = @Value(MetaId) @Value(MetaId) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> FeatureMerger_4 [REQUESTOR]
FeatureMerger_4
    ATTR_ACCUM_MODE = Merge Supplier
    ATTR_CONFLICT_RES_LOOKUP = REQUESTOR_IF_CONFLICT
    IGNORE_NULLS = No
    JOIN_KEYS = @Value(ClassId) @Value(MetaId) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> BulkAttributeRenamer_2
BulkAttributeRenamer_2
    ATTRCHOICE_ACTION = NONPROTECTEDFME
    MODE_CHOICE = RENAME
    PATTERN_ACTION_DISP = ADDPREFIX
    REPLACE_STR = subclass_
    ATTRCHOICE = All Attributes
    -> FeatureMerger_6 [SUPPLIER]
Object (reader MSSQL_ADO_1)
    attributes: ObjectId identity, ClassId integer, SubClassid integer, Id integer, Name char(50), IsRegistered smallint, SiteId integer
    -> FeatureMerger_5 [REQUESTOR]
FeatureMerger_5
    ATTR_ACCUM_MODE = Merge Supplier
    ATTR_CONFLICT_RES_LOOKUP = REQUESTOR_IF_CONFLICT
    IGNORE_NULLS = No
    JOIN_KEYS = @Value(ClassId) @Value(class_MetaId) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> AttributeManager
AttributeManager
    ATTR_TABLE:
      REMOVE IsRegistered (int16)
      SET_TO SiteId (int32)
      SET_TO ToolTip (varchar(50))
      SET_TO class_MetaId (int32)
      SET_TO class_CanAddSubclass (int16)
      SET_TO class_SpecialRegIsActive (int16)
      SET_TO class_InfoGroupDefId (int32)
      SET_TO class_DefaultAttributeDefId (int32)
      RENAME_SET_VALUE class_Name > Class (char(50))
      REMOVE class_Description (varchar(100))
      REMOVE class_ToolTip (varchar(50))
      REMOVE class_Help (buffer)
      REMOVE class_IsVisible (int16)
    USER_EXPOSED_ATTRIBUTES = ToolTip
    -> FeatureMerger_6 [REQUESTOR]
FeatureMerger_6
    ATTR_ACCUM_MODE = Merge Supplier
    ATTR_CONFLICT_RES_LOOKUP = REQUESTOR_IF_CONFLICT
    IGNORE_NULLS = No
    JOIN_KEYS = @Value(SubClassid) @Value(subclass_MetaId) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> AttributeManager_2
    UNMERGED_REQUESTOR -> AttributeManager_2
AttributeManager_2
    ATTR_TABLE:
      RENAME_SET_VALUE ObjectId > object_id (int32)
      REMOVE SubClassid (int32)
      RENAME_SET_VALUE Id > IntrasisId (int32)
      REMOVE SiteId (int32)
      REMOVE ToolTip (varchar(50))
      REMOVE class_MetaId (int32)
      REMOVE class_CanAddSubclass (int16)
      REMOVE class_SpecialRegIsActive (int16)
      REMOVE class_InfoGroupDefId (int32)
      REMOVE class_DefaultAttributeDefId (int32)
      REMOVE class_VersionReferenceId (int32)
      REMOVE class_ExternalId (int32)
      REMOVE subclass_MetaId (int32)
      REMOVE subclass_ClassId (int32)
      REMOVE subclass_IsInUse (int16)
      REMOVE subclass_VersionReferenceId (int32)
      RENAME_SET_VALUE subclass_Name > SubClass (char(50))
      REMOVE subclass_Description (varchar(100))
      REMOVE subclass_ToolTip (varchar(50))
      REMOVE subclass_Help (buffer)
      REMOVE subclass_IsVisible (int16)
      REMOVE subclass_ExternalId (int32)
      REMOVE subclass_CanAddSubclass (int16)
      REMOVE subclass_SpecialRegIsActive (int16)
      REMOVE subclass_InfoGroupDefId (int32)
      REMOVE subclass_DefaultAttributeDefId (int32)
    -> FeatureMerger_9 [SUPPLIER]

Bookmark: shapefiles
ILine (reader SHAPEFILE_1)
    attributes: ShapeID number(15,0), MetaID number(15,0)
    -> Tester
IMultiP (reader SHAPEFILE_1)
    attributes: ShapeID number(15,0), MetaID number(15,0)
    -> Tester
IPoint (reader SHAPEFILE_1)
    attributes: ShapeID number(15,0), MetaID number(15,0)
    -> Tester
IPolygon (reader SHAPEFILE_1)
    attributes: ShapeID number(15,0), MetaID number(15,0)
    -> Tester
Line (reader SHAPEFILE_1)
    attributes: ShapeID number(15,0), MetaID number(15,0)
    -> Tester
LLine (reader SHAPEFILE_1)
    attributes: Date varchar(20), ShapeID number(15,0), MetaID number(15,0)
    -> Tester
LMultiP (reader SHAPEFILE_1)
    attributes: Date varchar(20), ShapeID number(15,0), MetaID number(15,0)
    -> Tester
LPoint (reader SHAPEFILE_1)
    attributes: Date varchar(20), ShapeID number(15,0), MetaID number(15,0)
    -> Tester
LPolygon (reader SHAPEFILE_1)
    attributes: Date varchar(20), ShapeID number(15,0), MetaID number(15,0)
    -> Tester
MultiP (reader SHAPEFILE_1)
    attributes: ShapeID number(15,0), MetaID number(15,0)
    -> Tester
Point (reader SHAPEFILE_1)
    attributes: ShapeID number(15,0), MetaID number(15,0)
    -> Tester
Polygon (reader SHAPEFILE_1)
    attributes: ShapeID number(15,0), MetaID number(15,0)
    -> Tester

Bookmark: features
Tester
    BOOL_OP = OR
    TEST_CLAUSE = TEST 1 = 1
    TEST_MODE = TEST
    PASSED -> FeatureMerger_7 [REQUESTOR]
GeoObject (reader MSSQL_ADO_1)
    attributes: ObjectId integer, MeasurementJobId integer, MetaId integer, ShapeId identity
    -> FeatureMerger_7 [SUPPLIER]
FeatureMerger_7
    ATTR_ACCUM_MODE = Merge Supplier
    ATTR_CONFLICT_RES_LOOKUP = REQUESTOR_IF_CONFLICT
    CLEANING_TOLERANCE_LOOKUP = AUTO
    CONNECT_Z_MODE_LOOKUP = FIRST_WINS
    GEOM_TYPE_VAL = POLYGONS
    IGNORE_NULLS = No
    JOIN_KEYS = @Value(ShapeID) @Value(ShapeId) AUTO
    MERGE_TYPE_VAL = GEOM_AND_ATTRS
    PROCESS_DUPS = YES
    REJECT_NULL_MISSING_KEYS = No
    SUPPLIERS_FIRST = No
    ATTR_CONFLICT_RES = Use Requestor
    CLEANING_TOLERANCE = Automatic
    CONNECT_Z_MODE = First Wins
    GEOM_TYPE = Build Polygons
    MERGE_TYPE = Attributes and Geometry
    MERGED -> GeometryFilter
GeometryFilter
    FILTER_MODE = SIMPLE
    FILTER_MULTI = FILTER_TYPES]Null Point Line Area]FILTER_TYPES_Simple]Null Point Line Area
    FILTER_TYPES = Null Point Line Area
    FILTER_TYPES_Simple = Null Point Line Area
    Point -> AttributeManager_3
    Curve -> AttributeManager_4
    Area -> AttributeManager_5
AttributeManager_3
    ATTR_TABLE = SET_TO spatial_type (varchar(5)) = Point
    -> AttributeManager_6
AttributeManager_4
    ATTR_TABLE = SET_TO spatial_type (varchar(8)) = Polyline
    -> AttributeManager_6
AttributeManager_5
    ATTR_TABLE = SET_TO spatial_type (varchar(5)) = Point
    -> AttributeManager_6
AttributeManager_6
    -> FeatureMerger_8 [REQUESTOR]
GeoRel (reader MSSQL_ADO_1)
    attributes: ObjectId integer, GeoObjectId integer
    -> BulkAttributeRenamer_3
BulkAttributeRenamer_3
    ATTRCHOICE_ACTION = NONPROTECTEDFME
    MODE_CHOICE = RENAME
    PATTERN_ACTION_DISP = ADDPREFIX
    REPLACE_STR = GeoRel2_
    ATTRCHOICE = All Attributes
    -> FeatureMerger_8 [SUPPLIER]
FeatureMerger_8
    ATTR_ACCUM_MODE = Prefix Supplier
    CLEANING_TOLERANCE_LOOKUP = AUTO
    CONNECT_Z_MODE_LOOKUP = FIRST_WINS
    GEOM_TYPE_VAL = POLYGONS
    IGNORE_NULLS = No
    JOIN_KEYS = @Value(ObjectId) @Value(GeoRel2_GeoObjectId) AUTO
    LIST_NAME = list
    MERGE_TYPE_VAL = ATTRIBUTES
    PROCESS_DUPS = YES
    REJECT_NULL_MISSING_KEYS = No
    SUPPLIERS_FIRST = No
    SUPPLIER_PREFIX = sup
    CLEANING_TOLERANCE = Automatic
    CONNECT_Z_MODE = First Wins
    GEOM_TYPE = Build Polygons
    MERGE_TYPE = Attributes Only
    MERGED -> ListExploder
ListExploder
    ATTR_CONFLICT_RES_LOOKUP = INCOMING_IF_CONFLICT
    INDEX_ATTR = _element_index
    LIST_ATTR = list{}
    ATTR_ACCUM_MODE = Merge List Attributes
    ATTR_CONFLICT_RES = Use List Attribute Values
    ELEMENTS -> AttributeManager_8
AttributeManager_8
    -> FeatureMerger_9 [REQUESTOR]
FeatureMerger_9
    ATTR_ACCUM_MODE = Merge Supplier
    ATTR_CONFLICT_RES_LOOKUP = REQUESTOR_IF_CONFLICT
    CLEANING_TOLERANCE_LOOKUP = AUTO
    CONNECT_Z_MODE_LOOKUP = FIRST_WINS
    GEOM_TYPE_VAL = POLYGONS
    IGNORE_NULLS = No
    JOIN_KEYS = @Value(GeoRel2_ObjectId) @Value(object_id) AUTO
    MERGE_TYPE_VAL = GEOM_AND_ATTRS
    PROCESS_DUPS = YES
    REJECT_NULL_MISSING_KEYS = No
    SUPPLIERS_FIRST = No
    ATTR_CONFLICT_RES = Use Requestor
    CLEANING_TOLERANCE = Automatic
    CONNECT_Z_MODE = First Wins
    GEOM_TYPE = Build Polygons
    MERGE_TYPE = Attributes and Geometry
    MERGED -> Counter_3
Counter_3
    CNT_ATTR = _counter
    DOMAIN = counter
    SCOPE = Global
    START = 1
    -> AttributeManager_7
Note: R
AttributeManager_7
    ATTR_TABLE:
      RENAME_SET_DEFAULT Name (char(50))
      RENAME_SET_DEFAULT Class (char(50))
      RENAME_SET_DEFAULT SubClass (char(50))
      SET_TO spatial_type (varchar(5)) = FME_CONDITIONAL:DEFAULT_VALUE'_FME_NO_OP_'BOOL_OP;OR;COMPOSITE_TEST;1;TEST @GeometryType() = fme_polygon'Polygon'BOOL_OP;OR;COMPOSITE_TEST;1;TEST @GeometryType() = fme_line'Polyline'BOOL_OP;OR;COMPOSITE_TEST;1;TEST @GeometryType() = fme_point'Point'BOOL_OP;OR;COMPOSITE_TEST;1;TEST @GeometryType() = fme_multipoint'Multipoint'FME_NUM_CONDITIONS5___
      RENAME_SET_VALUE GeoRel2_ObjectId > object_id (int32)
      RENAME_SET_VALUE GeoRel2_GeoObjectId > GeoObjectId (int32)
      RENAME_SET_DEFAULT ShapeID (number(15,0))
      RENAME_SET_DEFAULT MetaID (number(15,0))
      RENAME_SET_DEFAULT Date (varchar(20))
      RENAME_SET_DEFAULT ObjectId (int32)
      RENAME_SET_DEFAULT MeasurementJobId (int32)
      RENAME_SET_DEFAULT IntrasisId (int32)
      RENAME_SET_VALUE _counter > fid (int64)
      REMOVE ClassId (int32)
      REMOVE _element_index (uint32)
      REMOVE object_id (int32)
      REMOVE supGeoRel2_ObjectId (int32)
      REMOVE supGeoRel2_GeoObjectId (int32)
      REMOVE MetaId (int32)
      REMOVE ShapeId (int32)
    USER_EXPOSED_ATTRIBUTES = ShapeID,MetaID,Date,ObjectId,MeasurementJobId,MetaId,ShapeId,spatial_type,GeoRel2_ObjectId,GeoRel2_GeoObjectId,IntrasisId,Name,Class,SubClass
    -> FeatureWriter [features]
    -> FeatureMerger [REQUESTOR] [off]
    -> GeometryFilter_2
GeometryFilter_2
    FILTER_MODE = SIMPLE
    FILTER_MULTI = FILTER_TYPES]Null Point Line Area Surface]FILTER_TYPES_Simple]Null Point Line Area Surface
    FILTER_TYPES = Null Point Line Area Surface
    FILTER_TYPES_Simple = Null Point Line Area Surface
    Point -> point (writer OGCGEOPACKAGE_1)
    Curve -> line (writer OGCGEOPACKAGE_1)
    Area -> area (writer OGCGEOPACKAGE_1)
point (writer OGCGEOPACKAGE_1)
    attributes: name text(50), class text(50), subclass text(50), spatial_type text(5), geoobjectid integer, shapeid int, metaid int, date text(20), objectid integer, measurementjobid integer, intrasisid integer, fid int
line (writer OGCGEOPACKAGE_1)
    attributes: name text(50), class text(50), subclass text(50), spatial_type text(5), geoobjectid integer, shapeid int, metaid int, date text(20), objectid integer, measurementjobid integer, intrasisid integer, fid int
area (writer OGCGEOPACKAGE_1)
    attributes: name text(50), class text(50), subclass text(50), spatial_type text(5), geoobjectid integer, shapeid int, metaid int, date text(20), objectid integer, measurementjobid integer, intrasisid integer, fid int
Symbol (reader MSSQL_ADO_1) [off]
    attributes: SymbolId identity, MetaId integer, SymbolIndex smallint, Type char(30), Context char(30), Font char(30), IconReference char(50), SymbolSize integer
    -> AttributeValueMapper
AttributeValueMapper [off]
    LUT = MapPoint,Point,MapLine,Polyline,MapArea,Polygon
    MAPPING_DIRECTION = FORWARD
    SRC = Type
    VAL_ATTR = _looked_up
    -> FeatureMerger [SUPPLIER]
FeatureMerger [off]
    ATTR_ACCUM_MODE = Merge Supplier
    ATTR_CONFLICT_RES_LOOKUP = REQUESTOR_IF_CONFLICT
    IGNORE_NULLS = No
    JOIN_KEYS = @Value(ClassId) @Value(MetaId) AUTO @Value(spatial_type) @Value(_looked_up) AUTO
    MERGE_TYPE_VAL = GEOM_AND_ATTRS
    PROCESS_DUPS = NO
    REJECT_NULL_MISSING_KEYS = No
    SUPPLIERS_FIRST = No
    ATTR_CONFLICT_RES = Use Requestor
    MERGE_TYPE = Attributes and Geometry
    MERGED -> FeatureWriter [features]
    UNMERGED_REQUESTOR -> FeatureWriter [features]
FeatureWriter [off]
    CONFIG_PARAMETERS = ESCAPE_COMMAS_IN_FTP_FORMAT_PARAMETERS,no
    DATASET = $(DestDataset_OGCGEOPACKAGE)
    DATASET_ATTR = _dataset
    FEATURE_TYPE_LIST_ATTR = _feature_types
    FORMAT = OGCGEOPACKAGE
    OGCGEOPACKAGE_COORDINATE_SYSTEM_GRANULARITY = FEATURE_TYPE
    OGCGEOPACKAGE_DESTINATION_DATASETTYPE_VALIDATION = Yes
    OGCGEOPACKAGE_ENCODE_FEATURE_TYPE_AND_ATTR_NAMES = YES
    OGCGEOPACKAGE_ENFORCE_GEOMETRY_COLUMN_CONSTRAINTS = YES
    OGCGEOPACKAGE_EXPOSE_PRIMARY_KEY_ATTRIBUTE = YES
    OGCGEOPACKAGE_OVERWRITE_DATASET = NO
    OGCGEOPACKAGE_TRANSACTION_SIZE = 5000
    OGCGEOPACKAGE_VERSION = 1.2
    OGCGEOPACKAGE_WRITE_NULLS = YES
    TOTAL_FEATURES_WRITTEN_ATTR = _total_features_written
