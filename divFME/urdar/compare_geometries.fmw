FME workspace compare_geometries.fmw

Parameters:
- SourceDataset_OGCGEOPACKAGE = C:\Users\krima354\Work Folders\Documents\kicki_arbetsfiler\urdar_arbetsfiler\alla40utanfor20230918_2.gpkg   # GeoPackage File
- SourceDataset_OGCGEOPACKAGE_3 = C:\Users\krima354\Work Folders\Documents\kicki_arbetsfiler\urdar_arbetsfiler\alla39utanforFranLocalhost.gpkg   # GeoPackage File

Readers:
- OGCGEOPACKAGE_1: OGCGEOPACKAGE from $(SourceDataset_OGCGEOPACKAGE) in EPSG:3006
- OGCGEOPACKAGE_2: OGCGEOPACKAGE from $(SourceDataset_OGCGEOPACKAGE_3) in EPSG:3006

alla40 (reader OGCGEOPACKAGE_1)
    attributes: numGeoObj int, pk mediumint, SiteId text, Plats text, Lst Dnr text, Raä Dnr text, Inventarienummer text, Projektkod text, Projektnamn text, Projektledare text, Uppdragsgivare text, Exploateringstyp text, Undersökningstyp text, Slutdatum text, Beskrivning text, fid int, Value text, id int,PrimaryKey
    -> BoundingBoxAccumulator
    -> AttributeManager
BoundingBoxAccumulator
    ACCUM_ATTRS_NAME = Use Attributes From One Feature
    GROUP_BY = SiteId
    BOUNDING_BOX -> ChangeDetector [REVISED]
AttributeManager
    ATTR_TABLE = SET_TO idb = @LowerCase(@ReplaceString(@Value(SiteId),":","",caseSensitive=TRUE))
    -> FeatureMerger [REQUESTOR]
alla39 (reader OGCGEOPACKAGE_2)
    attributes: idb text, id int,PrimaryKey
    -> BoundingBoxAccumulator_2
    -> FeatureMerger [SUPPLIER]
BoundingBoxAccumulator_2
    ACCUM_ATTRS_NAME = Use Attributes From One Feature
    GROUP_BY = idb
    BOUNDING_BOX -> ChangeDetector [ORIGINAL]
ChangeDetector
    BLANK_AND_MISSING_NAMES_TRAITS_DIFFER = No
    CHECK_COORDINATE_SYSTEMS = No
    LENIENT_MATCH = No
    MATCH = FULL
    UNCHANGED_OUTPUT = Output Original
    UPSERT_MODE = No
    UNCHANGED -> GeometryRemover
GeometryRemover
    -> FeatureMerger_2 [REQUESTOR]
FeatureMerger
    ATTR_ACCUM_MODE = Merge Supplier
    ATTR_CONFLICT_RES = Use Requestor
    IGNORE_NULLS = No
    JOIN_KEYS = @Value(idb) @Value(idb) AUTO
    MERGE_TYPE = Attributes Only
    PROCESS_DUPS = NO
    REJECT_NULL_MISSING_KEYS = No
    SUPPLIERS_FIRST = No
    MERGED -> FeatureMerger_2 [SUPPLIER]
FeatureMerger_2
    ATTR_ACCUM_MODE = Merge Supplier
    ATTR_CONFLICT_RES = Use Requestor
    IGNORE_NULLS = No
    JOIN_KEYS = @Value(idb) @Value(idb) AUTO
    MERGE_TYPE = Attributes and Geometry
    PROCESS_DUPS = NO
    REJECT_NULL_MISSING_KEYS = No
    SUPPLIERS_FIRST = No
    MERGED -> TestFilter_2
TestFilter_2
    DEFAULT_VALUE = <UNFILTERED>
    PASSED_TEST_GROUP_OUTPUT = FIRST
    TEST_LIST = "BOOL_OP,OR,COMPOSITE_TEST,""""""1"""""",TEST_CLAUSE,TEST @Value(Value) = 3021",3021,"BOOL_OP,OR,COMPOSITE_TEST,""""""1"""""",TEST_CLAUSE,TEST @Value(Value) = 3006",3006,"BOOL_OP,OR,COMPOSITE_TEST,""""""1"""""",TEST_CLAUSE,TEST @Value(Value) = 3019",3019,"BOOL_OP,OR,COMPOSITE_TEST,""""""1"""""",TEST_CLAUSE,TEST @Value(Value) = 4308",4308,"BOOL_OP,OR,COMPOSITE_TEST,""""""1"""""",TEST_CLAUSE,TEST @Value(Value) = 0",0
    3021 -> GtransReprojector
GtransReprojector
    INTERPOLATION_TYPE_NAME = Nearest Neighbor
    RASTER_CELL_SIZE = Square Cells
    RASTER_TOLERANCE = 0.0
    TRANSLATION_FILE = $(FME_HOME)Reproject\Gtrans\Sys\SW99TM-RT90.tfi
AreaOnAreaOverlayer
    ACCUM_ATTRS_NAME = Use Attributes From One Feature
    CLEANING_TOLERANCE = Automatic
    CONNECT_Z_MODE = First Wins
    DEAGGREGATE_INPUT = Yes
    OVC_ATTR = _overlaps
