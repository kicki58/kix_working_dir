FME workspace fixExcel2aggragate.fmw

Parameters:
- SourceDataset_XLSXR = C:\Users\krima354\Box\Urdar\gpkg_csv\alla_gpkg_csv_slutleverans\tillRAA20240624_v4.xlsx   # Source Microsoft Excel File(s)
- DestDataset_XLSXW = C:\Users\krima354\Box\Urdar\gpkg_csv\alla_gpkg_csv_slutleverans\kkk14.xlsx   # Destination Microsoft Excel File

Readers:
- XLSXR_1: XLSXR from $(SourceDataset_XLSXR)

Writers:
- XLSXW_1: XLSXW to $(DestDataset_XLSXW)

slutleverans_v4 (reader XLSXR_1)
    attributes: master_site_archive char(10), master_site_name char(53), UUID_final char(36), UUID_final_finns char(3), UUID_final_link char(76), master_UUID char(36), master_UUID_finns char(3), link_master_uuid char(76), master_Uppdaterat UUID char(36), master_Uppdaterat UUID_finns char(3), master_link_Uppdaterat_uuid char(76), UUID_typ char(22), E number(21,13), N number(21,13), databas char(10), proj_info_intrasis_archive char(10), proj_info_pk number(1,0), proj_info_SiteId char(10), proj_info_Plats char(28), proj_info_Lst Dnr char(35), proj_info_Raä Dnr char(41), proj_info_Inventarienummer char(12), proj_info_Projektkod char(23), proj_info_Projektnamn char(54), proj_info_Projektledare char(37), proj_info_Uppdragsgivare char(44), proj_info_Exploateringstyp char(27), proj_info_Undersökningstyp char(30), proj_info_Slutdatum char(10), proj_info_Beskrivning char(4944),
      _socken_concatenated char(259), _socken_antal number(2,0), _kommun_concatenated char(34), _kommun_antal number(1,0), _landskap_concatanted char(29), _landskap_antal number(1,0), _lan_concatenated char(29), _lan_antal number(1,0), uo_id char(36), uo_uppdragsnummer number(9,0), uo_beslutande_myndighet char(40), uo_beslutsdatum date, uo_diarienummer char(16), uo_uppdragstyp char(29), uo_utforande_organisation char(55), uo_nollresultat char(3), uo_url char(90), uo_status char(10), uo_lan char(26), uo_kommun char(30), uo_socken char(151), epsg number(4,0)
    -> AttributeManager_11
AttributeManager_11
    ATTR_TABLE = SET_TO efterbearbetning (varchar(200)) = @Value(UUID_typ)
    -> AttributeFilter
AttributeFilter
    ATTR_NAME = UUID_typ
    ATTR_VALUES = <Empty>,<Missing>,<Null>,<Unfiltered>,ej lyckats georeferera,empty,extern,noUUID,uuidSattMen_empty
    <UNFILTERED> -> AttributeFilter_3
    ej lyckats georeferera -> StatisticsCalculator_2
    ej lyckats georeferera -> c (writer XLSXW_1)
    empty -> StatisticsCalculator_3
    empty -> c (writer XLSXW_1)
    extern -> StatisticsCalculator_4
    extern -> c (writer XLSXW_1)
    noUUID -> StatisticsCalculator_5
    noUUID -> c (writer XLSXW_1)
    uuidSattMen_empty -> StatisticsCalculator_6
    uuidSattMen_empty -> c (writer XLSXW_1)
AttributeFilter_3
    ATTR_NAME = UUID_final_finns
    ATTR_VALUES = <Empty>,<Missing>,<Null>,<Unfiltered>,FME_NULL_VALUE,JA,NEJ
    <NULL> -> AttributeFilter_2
    JA -> AttributeManager_10
    NEJ -> AttributeFilter_2
AttributeFilter_2
    ATTR_NAME = master_UUID_finns
    ATTR_VALUES = <Empty>,<Missing>,<Null>,<Unfiltered>,FME_NULL_VALUE,JA,NEJ
    <NULL> -> AttributeManager_9
    JA -> AttributeManager_10
    NEJ -> AttributeManager_9
AttributeManager_9
    ATTR_TABLE = SET_TO efterbearbetning (varchar(7)) = noUUID
    -> StatisticsCalculator_5
    -> c (writer XLSXW_1)
AttributeManager_10
    ATTR_TABLE = SET_TO efterbearbetning (varchar(22)) = UUID_finns&inomSverige
    -> Tester
Tester
    BOOL_OP = OR
    TEST_CLAUSE = TEST 1 = 1
    TEST_MODE = TEST
    PASSED -> c (writer XLSXW_1)
    PASSED -> AttributeManager_3
c (writer XLSXW_1)
    attributes: efterbearbetning string(200), master_site_archive string(10), master_site_name string(53), UUID_final string(36), UUID_final_finns string(3), UUID_final_link string(76), master_UUID string(36), master_UUID_finns string(3), link_master_uuid string(76), master_Uppdaterat UUID string(36), master_Uppdaterat UUID_finns string(3), master_link_Uppdaterat_uuid string(76), UUID_typ string(22), E number(21), N number(21), databas string(10), proj_info_intrasis_archive string(10), proj_info_pk number(1), proj_info_SiteId string(10), proj_info_Plats string(28), proj_info_Lst Dnr string(35), proj_info_Raä Dnr string(41), proj_info_Inventarienummer string(12), proj_info_Projektkod string(23), proj_info_Projektnamn string(54), proj_info_Projektledare string(37), proj_info_Uppdragsgivare string(44), proj_info_Exploateringstyp string(27), proj_info_Undersökningstyp string(30), proj_info_Slutdatum string(10),
      proj_info_Beskrivning string(4944), _socken_concatenated string(259), _socken_antal number(2), _kommun_concatenated string(34), _kommun_antal number(1), _landskap_concatanted string(29), _landskap_antal number(1), _lan_concatenated string(29), _lan_antal number(1), uo_id string(36), uo_uppdragsnummer number(9), uo_beslutande_myndighet string(40), uo_beslutsdatum date(20), uo_diarienummer string(16), uo_uppdragstyp string(29), uo_utforande_organisation string(55), uo_nollresultat string(3), uo_url string(90), uo_status string(10), uo_lan string(26), uo_kommun string(30), uo_socken string(151), epsg number(4)
Aggregator
    ACCUM_ATTRS_NAME = Merge Incoming Attributes
    AGGREGATE_TYPE = Homogeneous Collection (If Possible)
    MODE = Geometry - Assemble One Level
    SEP = ,
    AGGREGATE -> AttributeManager_2
AttributeManager_2
    ATTR_TABLE = SET_TO summa (varchar(200)) = @sum(@Value(ej_lyckats_georeferera),@Value(empty),@Value(extern),@Value(noUUID),@Value(UUID_finns&inomSverige),@Value(uuidSattMenEmpty))
    -> sammanfattning_antal (writer XLSXW_1)
sammanfattning_antal (writer XLSXW_1)
    attributes: UUID_finns&inomSverige number(20), ej_lyckats_georeferera number(20), empty number(20), extern number(20), uuidSattMenEmpty number(20), noUUID number(20), summa string(200)

Bookmark: summering
StatisticsCalculator_2
    ATTR_ACCUM_MODE = None
    CALCULATION_MODE = NUMERIC
    FEAT_STATS = UUID_final,NUMERIC_MODE,,,COUNT,,,,,,,,,,
    SUMMARY -> AttributeManager_4
AttributeManager_4
    ATTR_TABLE = RENAME_SET_VALUE UUID_final.total_count > ej_lyckats_georeferera (uint64)
    -> Aggregator
StatisticsCalculator_3
    ATTR_ACCUM_MODE = None
    CALCULATION_MODE = NUMERIC
    FEAT_STATS = UUID_final,NUMERIC_MODE,,,COUNT,,,,,,,,,,
    SUMMARY -> AttributeManager_5
AttributeManager_5
    ATTR_TABLE = RENAME_SET_VALUE UUID_final.total_count > empty (uint64)
    -> Aggregator
StatisticsCalculator_4
    ATTR_ACCUM_MODE = None
    CALCULATION_MODE = NUMERIC
    FEAT_STATS = UUID_final,NUMERIC_MODE,,,COUNT,,,,,,,,,,
    SUMMARY -> AttributeManager_7
AttributeManager_7
    ATTR_TABLE = RENAME_SET_VALUE UUID_final.total_count > extern (uint64)
    -> Aggregator
StatisticsCalculator_5
    ATTR_ACCUM_MODE = None
    CALCULATION_MODE = NUMERIC
    FEAT_STATS = UUID_final,NUMERIC_MODE,,,COUNT,,,,,,,,,,
    SUMMARY -> AttributeManager_6
AttributeManager_6
    ATTR_TABLE = RENAME_SET_VALUE UUID_final.total_count > noUUID (uint64)
    -> Aggregator
AttributeManager_3
    -> StatisticsCalculator
StatisticsCalculator
    ATTR_ACCUM_MODE = None
    CALCULATION_MODE = NUMERIC
    FEAT_STATS = UUID_final,NUMERIC_MODE,,,COUNT,,,,,,,,,,
    SUMMARY -> AttributeManager
AttributeManager
    ATTR_TABLE = RENAME_SET_VALUE UUID_final.total_count > UUID_finns&inomSverige (uint64)
    -> Aggregator
StatisticsCalculator_6
    ATTR_ACCUM_MODE = None
    CALCULATION_MODE = NUMERIC
    FEAT_STATS = UUID_final,NUMERIC_MODE,,,COUNT,,,,,,,,,,
    SUMMARY -> AttributeManager_8
AttributeManager_8
    ATTR_TABLE = RENAME_SET_VALUE UUID_final.total_count > uuidSattMenEmpty (uint64)
    -> Aggregator
