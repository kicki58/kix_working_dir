FME workspace projInfoAccumulator.fmw

Parameters:
- SourceDataset_OGCGEOPACKAGE = C:\Users\krima354\Box\Urdar\urdar_gpkg_export_230630\klara3006\b20001.gpkg   # GeoPackage File
- intrasis_archive = v2009027   # Intrasis_archive
- DestDataset_OGCGEOPACKAGE = C:\Users\krima354\Box\Urdar\urdar_gpkg_export_230630\klara3006\proj_info.gpkg   # GeoPackage File

Readers:
- OGCGEOPACKAGE_1: OGCGEOPACKAGE from $(SourceDataset_OGCGEOPACKAGE)

Writers:
- OGCGEOPACKAGE_2: OGCGEOPACKAGE to $(DestDataset_OGCGEOPACKAGE) in EPSG:3006

project_information (reader OGCGEOPACKAGE_1)
    attributes: pk mediumint, SiteId text, Plats text, Lst Dnr text, Raä Dnr text, Inventarienummer text, Projektkod text, Projektnamn text, Projektledare text, Uppdragsgivare text, Exploateringstyp text, Undersökningstyp text, Slutdatum text, Beskrivning text, fid int,PrimaryKey
    -> AttributeManager_2
AttributeManager_2
    ATTR_TABLE:
      SET_TO fid
      SET_TO Identifierare = $(intrasis_archive)
      SET_TO Relaterade URI:er
      SET_TO Uppdragsnummer
      SET_TO Uppdragstyp = @Value(Exploateringstyp)
      SET_TO Beslutande myndighet
      SET_TO Länsstyrelsens diarienummer = @Value(Lst Dnr)
      SET_TO Lämningsnummer
      SET_TO Lämningstyp
      SET_TO Land
      SET_TO Landskap
      SET_TO Län
      SET_TO Kommun
      SET_TO Socken
      SET_TO Platsnamn = @Value(Plats)
      SET_TO Diarienummer RAÄ = @Value(Raä Dnr)
      SET_TO Arkivarienotering
    USER_EXPOSED_ATTRIBUTES = Attributtyp iipax,Exempelvärde,internt namn iipax,Namn Intrasis (gisli tabell),obligatoriskt,Var hämtas data?,Värden batchleverans av UV intrasis,Arkivarienotering,Beslutande myndighet,Diarienummer RAÄ,Identifierare,Kommun,Land,Landskap,Lämningsnummer,Lämningstyp,Län,Länsstyrelsens diarienummer,Platsnamn,Relaterade URI:er,Socken,Uppdragsnummer,Uppdragstyp,pk,SiteId,Plats,Lst Dnr,Raä Dnr,Inventarienummer,Projektkod,Projektnamn,Projektledare,Uppdragsgivare,Exploateringstyp,Undersökningstyp,Slutdatum,Beskrivning,fid
    -> AttributeManager
AttributeManager
    ATTR_TABLE:
      REMOVE pk
      REMOVE SiteId
      REMOVE Plats
      REMOVE Lst Dnr
      REMOVE Raä Dnr
      REMOVE Inventarienummer
      REMOVE Projektkod
      REMOVE Projektnamn
      REMOVE Projektledare
      REMOVE Uppdragsgivare
      REMOVE Exploateringstyp
      REMOVE Undersökningstyp
      REMOVE Slutdatum
    -> projec_information (writer OGCGEOPACKAGE_2)
projec_information (writer OGCGEOPACKAGE_2)
    attributes: Beskrivning text, fid int,PrimaryKey, Identifierare text(200), Relaterade URI:er text(200), Uppdragsnummer text(200), Uppdragstyp text, Beslutande myndighet text(200), Länsstyrelsens diarienummer text, Lämningsnummer text(200), Lämningstyp text(200), Land text(200), Landskap text(200), Län text(200), Kommun text(200), Socken text(200), Platsnamn text, Diarienummer RAÄ text, Arkivarienotering text(200)
