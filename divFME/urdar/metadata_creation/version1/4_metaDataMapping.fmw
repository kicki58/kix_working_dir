FME workspace 4_metaDataMapping.fmw

Parameters:
- DestDataset_XLSXW = C:\Users\krima354\Downloads\Databaser-mappning-metadata-Urdar-2023-09-07.xlsx   # Destination Microsoft Excel File
- SourceDataset_OGCGEOPACKAGE_3 = C:\Users\krima354\Work Folders\Documents\kicki_arbetsfiler\slask\siteinfo3.gpkg   # GeoPackage File

Readers:
- OGCGEOPACKAGE_2: OGCGEOPACKAGE from $(SourceDataset_OGCGEOPACKAGE_3) in EPSG:3006

Writers:
- XLSXW_1: XLSXW to $(DestDataset_XLSXW)

siteinfo (reader OGCGEOPACKAGE_2)
    attributes: geom_intrasis_archive text(200), _socken_concatenated text, _socken_antal int, _kommun_concatenated text, _landskap_antal int, _kommun_antal int, _lan_concatenated text, _landskap_concatanted text, _lan_antal int, master_site_name text(54), master_kmr_uppdragsnummer int, master_kmr_id text(37), master_Kommentar text(685), _uppdragsomraden_antal int, kmr_id_traff_i_uom text(200), _list_index int, uom_id text(255), uom_uppdragsnummer text(9), uom_beslutande_myndighet text(255), uom_beslutsdatum date, uom_diarienummer text(255), uom_uppdragstyp text(255), uom_utforande_organisation text(255), uom_nollresultat text(9), uom_url text(255), uom_status text(255), uom_lan text, uom_kommun text, uom_socken text, uom_fid int,
      uom_fme_rejection_code text, proj_info_Beskrivning text(1804), proj_info_fid text(1), proj_info_Identifierare text(17), proj_info_Relaterade URI:er text(1), proj_info_Uppdragsnummer text(1), proj_info_Uppdragstyp text(50), proj_info_Beslutande myndighet text(1), proj_info_Länsstyrelsens diarienummer text(42), proj_info_Lämningsnummer text(1), proj_info_Lämningstyp text(1), proj_info_Land text(1), proj_info_Landskap text(1), proj_info_Län text(1), proj_info_Kommun text(1), proj_info_Socken text(1), proj_info_Platsnamn text(54), proj_info_Diarienummer RAÄ text(44), proj_info_Arkivarienotering text(1), geom_id int,PrimaryKey
    -> AttributeManager
    -> OBS!!! test-data all_info_on site (writer XLSXW_1)
OBS!!! test-data all_info_on site (writer XLSXW_1)
    attributes: geom_intrasis_archive string(200), _socken_concatenated string(20), _socken_antal number(20), _kommun_concatenated string(20), _landskap_antal number(20), _kommun_antal number(20), _lan_concatenated string(20), _landskap_concatanted string(20), _lan_antal number(20), master_site_name string(54), master_kmr_uppdragsnummer number(20), master_kmr_id string(37), master_Kommentar string(685), _uppdragsomraden_antal number(20), kmr_id_traff_i_uom string(200), _list_index number(20), uom_id string(255), uom_uppdragsnummer string(9), uom_beslutande_myndighet string(255), uom_beslutsdatum date(20), uom_diarienummer string(255), uom_uppdragstyp string(255), uom_utforande_organisation string(255), uom_nollresultat string(9), uom_url string(255), uom_status string(255), uom_lan string(20), uom_kommun string(20), uom_socken string(20), uom_fid number(20),
      uom_fme_rejection_code string(20), proj_info_Beskrivning string(1804), proj_info_fid string(1), proj_info_Identifierare string(17), proj_info_Relaterade URI:er string(1), proj_info_Uppdragsnummer string(1), proj_info_Uppdragstyp string(50), proj_info_Beslutande myndighet string(1), proj_info_Länsstyrelsens diarienummer string(42), proj_info_Lämningsnummer string(1), proj_info_Lämningstyp string(1), proj_info_Land string(1), proj_info_Landskap string(1), proj_info_Län string(1), proj_info_Kommun string(1), proj_info_Socken string(1), proj_info_Platsnamn string(54), proj_info_Diarienummer RAÄ string(44), proj_info_Arkivarienotering string(1), geom_id number(20)
AttributeManager
    ATTR_TABLE:
      RENAME_SET_VALUE _socken_concatenated > Socken
      RENAME_SET_VALUE _kommun_concatenated > Kommun
      RENAME_SET_VALUE _lan_concatenated > Län
      RENAME_SET_VALUE _landskap_concatanted > Landskap
      REMOVE master_site_name
      SET_TO Identifierare = @Value(geom_intrasis_archive)_projectId?
      RENAME_SET_VALUE master_kmr_uppdragsnummer > Uppdragsnummer
      RENAME_SET_VALUE proj_info_Uppdragstyp > Uppdragstyp
      RENAME_SET_VALUE proj_info_Beslutande myndighet > Beslutande myndighet
      RENAME_SET_VALUE proj_info_Länsstyrelsens diarienummer > Länsstyrelsens diarienummer
      RENAME_SET_VALUE proj_info_Lämningsnummer > Lämningsnummer
      RENAME_SET_VALUE proj_info_Lämningstyp > Lämningstyp
      RENAME_SET_VALUE proj_info_Land > Land
      RENAME_SET_VALUE proj_info_Platsnamn > Platsnamn
      RENAME_SET_VALUE proj_info_Diarienummer RAÄ > Diarienummer RAÄ
      SET_TO E = @round(@XValue(),0)
      SET_TO N = @round(@YValue(),0)
    USER_EXPOSED_ATTRIBUTES = geopackage_type
    -> OBS!! testdata-mappning (writer XLSXW_1)
OBS!! testdata-mappning (writer XLSXW_1)
    attributes: Identifierare string(14), Relaterade URI:er string(18), Uppdragsnummer string(15), Uppdragstyp string(12), Beslutande myndighet string(21), Länsstyrelsens diarienummer string(29), Lämningsnummer string(16), Lämningstyp string(13), Land string(5), Landskap string(9), Län string(5), Kommun string(7), Socken string(7), Platsnamn string(10), Diarienummer RAÄ string(18), Arkivarienotering string(18), E string(2), N boolean(20)
