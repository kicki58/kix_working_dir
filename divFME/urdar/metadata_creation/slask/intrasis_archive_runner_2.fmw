FME workspace intrasis_archive_runner_2.fmw

Parameters:
- SourceDataset_CSV2 = C:\Users\krima354\Work Folders\Documents\kicki_arbetsfiler\slask\srid_urdar.csv   # Source CSV (Comma Separated Value) File(s)
- DestDataset_OGCGEOPACKAGE = C:\Users\krima354\Work Folders\Documents\kicki_arbetsfiler\slask\intrasis_archive_urdar_3006.gpkg   # GeoPackage File
- HOST_POSTGIS = 130.238.10.179   # Host
- USER_NAME_POSTGIS = kicki   # Username
- PASSWORD_POSTGIS =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   # Password
- PORT_POSTGIS = 5432   # Port
- SourceDataset_PATH = C:\Users\krima354\Box\Urdar\alla_gpkg_csv_20240117   # INCLUDE_WEB_BROWSER Source Folder and File Pathnames Folder

Readers:
- CSV2_1: CSV2 from $(SourceDataset_CSV2)
- PATH_1: PATH from $(SourceDataset_PATH)

CSV (reader CSV2_1)
    attributes: databas varchar(17), from_intrasis_epsg uint32
    -> WorkspaceRunner
WorkspaceRunner
    BLOCKING = Yes
    WORKSPACE_FILE = C:\Users\krima354\Work Folders\Documents\GitHub\kix_working_dir\divFME\urdar\intrasis_archive2.fmw
    WORKSPACE_PARAMETERS = source_POSTGIS,@Value(databas),DestDataset_OGCGEOPACKAGE,$(DestDataset_OGCGEOPACKAGE),HOST_POSTGIS,$(HOST_POSTGIS),USER_NAME_POSTGIS,$(USER_NAME_POSTGIS),PASSWORD_POSTGIS,$(PASSWORD_POSTGIS),PORT_POSTGIS,$(PORT_POSTGIS)
PATH (reader PATH_1)
    attributes: path_unix buffer, path_windows buffer, path_rootname buffer, path_filename buffer, path_extension buffer, path_directory_unix buffer, path_directory_windows buffer, path_type char(10)
