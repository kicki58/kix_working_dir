FME workspace projInfoAccumulator_v2.fmw

Parameters:
- SourceDataset_OGCGEOPACKAGE = C:\Users\krima354\Box\Urdar\urdar_gpkg_export_230630\klara3006\b20001.gpkg   # intrasis GeoPackage File
- DestDataset_OGCGEOPACKAGE = C:\Users\krima354\Box\Urdar\urdar_gpkg_export_230630\klara3006\proj_info.gpkg   # Dest GeoPackage File
- intrasis_archive =

Readers:
- OGCGEOPACKAGE_1: OGCGEOPACKAGE from $(SourceDataset_OGCGEOPACKAGE) in EPSG:3006

Writers:
- OGCGEOPACKAGE_2: OGCGEOPACKAGE to $(DestDataset_OGCGEOPACKAGE) in EPSG:3006

project_information (reader OGCGEOPACKAGE_1)
    attributes: pk mediumint, SiteId text, Plats text, Lst Dnr text, Raä Dnr text, Inventarienummer text, Projektkod text, Projektnamn text, Projektledare text, Uppdragsgivare text, Exploateringstyp text, Undersökningstyp text, Slutdatum text, Beskrivning text, fid int,PrimaryKey
    -> BulkAttributeRenamer
BulkAttributeRenamer
    ATTRCHOICE = All Attributes
    MODE_CHOICE = RENAME
    PATTERN_ACTION_DISP = ADDPREFIX
    REPLACE_STR = proj_info_
    -> AttributeManager_3
AttributeManager_3
    ATTR_TABLE = SET_TO proj_info_intrasis_archive = $(intrasis_archive)
    -> projec_information (writer OGCGEOPACKAGE_2)
projec_information (writer OGCGEOPACKAGE_2)
    attributes: proj_info_intrasis_archive text(200), proj_info_pk mediumint, proj_info_SiteId text, proj_info_Plats text, proj_info_Lst Dnr text, proj_info_Raä Dnr text, proj_info_Inventarienummer text, proj_info_Projektkod text, proj_info_Projektnamn text, proj_info_Projektledare text, proj_info_Uppdragsgivare text, proj_info_Exploateringstyp text, proj_info_Undersökningstyp text, proj_info_Slutdatum text, proj_info_Beskrivning text, proj_info_fid int
