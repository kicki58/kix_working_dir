FME workspace 3_metaDataCreator.fmw

Parameters:
- DestDataset_OGCGEOPACKAGE = C:\Users\krima354\Work Folders\Documents\kicki_arbetsfiler\slask\siteinfo3.gpkg   # GeoPackage File
- SourceDataset_OGCGEOPACKAGE = C:\Users\krima354\Work Folders\Documents\kicki_arbetsfiler\GETdata\arkeologiska_uppdrag_undersökningsområden_sverige.gpkg   # GeoPackage File
- SourceDataset_SHAPEFILE_5 = C:\Users\krima354\Work Folders\Documents\kicki_arbetsfiler\GETdata\shape_svenska_220223\KommunSweref99TM\Kommun_Sweref99TM_region.shp   # Source Esri Shapefile(s)
- SourceDataset_SHAPEFILE_4 = C:\Users\krima354\Work Folders\Documents\kicki_arbetsfiler\GETdata\shape_svenska_220223\LanSweref99TM\Lan_Sweref99TM_region.shp   # Source Esri Shapefile(s)
- SourceDataset_SHAPEFILE = C:\Users\krima354\Work Folders\Documents\kicki_arbetsfiler\GETdata\Kopia av landskap_shp\landskap\svelandskap_2010_rev_granser.shp   # Source Esri Shapefile(s)
- SourceDataset_OGCGEOPACKAGE_2 = C:\Users\krima354\Work Folders\Documents\kicki_arbetsfiler\GETdata\sockenstad.gpkg   # GeoPackage File
- SourceDataset_OGCGEOPACKAGE_7 = C:\Users\krima354\Work Folders\Documents\kicki_arbetsfiler\urdar_arbetsfiler\intrasis_archive_urdar_3006.gpkg   # GeoPackage File
- SourceDataset_XLSXR_3 = C:\Users\krima354\Box\Urdar\urdar_gpkg_export_230630\klara3006\project_info.xlsx   # Source Microsoft Excel File(s)
- SourceDataset_XLSXR = C:\Users\krima354\Downloads\UUID MASTER 20221007 (1).xlsx   # Source Microsoft Excel File(s)
- SourceDataset_OGCGEOPACKAGE_6 = C:\Users\krima354\Box\Urdar\urdar_gpkg_export_230630\klara3006\proj_info.gpkg   # GeoPackage File

Readers:
- SHAPEFILE_1: SHAPEFILE from $(SourceDataset_SHAPEFILE) in EPSG:3006
- SHAPEFILE_2: SHAPEFILE from $(SourceDataset_SHAPEFILE_5) in EPSG:3006
- SHAPEFILE_3: SHAPEFILE from $(SourceDataset_SHAPEFILE_4) in EPSG:3006
- OGCGEOPACKAGE_3: OGCGEOPACKAGE from $(SourceDataset_OGCGEOPACKAGE_2) in EPSG:3006
- OGCGEOPACKAGE_1: OGCGEOPACKAGE from $(SourceDataset_OGCGEOPACKAGE) in EPSG:3006
- OGCGEOPACKAGE_4: OGCGEOPACKAGE from $(SourceDataset_OGCGEOPACKAGE_7) in EPSG:3006
- XLSXR_1: XLSXR from $(SourceDataset_XLSXR)
- XLSXR_2: XLSXR from $(SourceDataset_XLSXR_3)
- OGCGEOPACKAGE_5: OGCGEOPACKAGE from $(SourceDataset_OGCGEOPACKAGE_6) in EPSG:3006

Writers:
- OGCGEOPACKAGE_2: OGCGEOPACKAGE to $(DestDataset_OGCGEOPACKAGE) in EPSG:3006

GeometryRemover
    -> FeatureMerger_3 [SUPPLIER]
proj_info (reader XLSXR_2) [off]
    attributes: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
projec_information (reader OGCGEOPACKAGE_5)
    attributes: Beskrivning text, Identifierare text(200), Relaterade URI:er text(200), Uppdragsnummer text(200), Uppdragstyp text, Beslutande myndighet text(200), Länsstyrelsens diarienummer text, Lämningsnummer text(200), Lämningstyp text(200), Land text(200), Landskap text(200), Län text(200), Kommun text(200), Socken text(200), Platsnamn text, Diarienummer RAÄ text, Arkivarienotering text(200), fid int,PrimaryKey
    -> BulkAttributeRenamer_4
BulkAttributeRenamer_4
    ATTRCHOICE = All Attributes
    MODE_CHOICE = RENAME
    PATTERN_ACTION_DISP = ADDPREFIX
    REPLACE_STR = proj_info_
    -> AttributeManager_8
AttributeManager_8
    -> FeatureMerger_3 [REQUESTOR]
Note: OBS Kolla upp denna
FeatureMerger_3
    ATTR_ACCUM_MODE = Merge Supplier
    ATTR_CONFLICT_RES = Use Requestor
    IGNORE_NULLS = No
    JOIN_KEYS = @Value(proj_info_Identifierare) @Value(geom_intrasis_archive) AUTO
    MERGE_TYPE = Attributes and Geometry
    PROCESS_DUPS = NO
    REJECT_NULL_MISSING_KEYS = No
    SUPPLIERS_FIRST = No
    MERGED -> siteinfo (writer OGCGEOPACKAGE_2)
siteinfo (writer OGCGEOPACKAGE_2)
    attributes: geom_intrasis_archive text(200), _socken_concatenated text, _socken_antal int, _kommun_concatenated text, _landskap_antal int, _kommun_antal int, _lan_concatenated text, _landskap_concatanted text, _lan_antal int, geom_id int,PrimaryKey, master_site_name text(54), master_kmr_uppdragsnummer int, master_kmr_id text(37), master_Kommentar text(685), _uppdragsomraden_antal int, kmr_id_traff_i_uom text(200), _list_index int, uom_id text(255), uom_uppdragsnummer text(9), uom_beslutande_myndighet text(255), uom_beslutsdatum date, uom_diarienummer text(255), uom_uppdragstyp text(255), uom_utforande_organisation text(255), uom_nollresultat text(9), uom_url text(255), uom_status text(255), uom_lan text, uom_kommun text, uom_socken text,
      uom_fid int, uom_fme_rejection_code text, proj_info_Beskrivning text(1804), proj_info_fid text(1), proj_info_Identifierare text(17), proj_info_Relaterade URI:er text(1), proj_info_Uppdragsnummer text(1), proj_info_Uppdragstyp text(50), proj_info_Beslutande myndighet text(1), proj_info_Länsstyrelsens diarienummer text(42), proj_info_Lämningsnummer text(1), proj_info_Lämningstyp text(1), proj_info_Land text(1), proj_info_Landskap text(1), proj_info_Län text(1), proj_info_Kommun text(1), proj_info_Socken text(1), proj_info_Platsnamn text(54), proj_info_Diarienummer RAÄ text(44), proj_info_Arkivarienotering text(1)

Bookmark: intrasis geometrier + UUID master
point (reader OGCGEOPACKAGE_4) [off]
    attributes: ObjectId mediumint, MetaId mediumint, SymbolId mediumint, the_raster text(200), _inside_x double, _inside_y double, _inside_z double, intrasis_archive text(200), id int,PrimaryKey
boundingbox (reader OGCGEOPACKAGE_4) [off]
    attributes: ObjectId mediumint, MetaId mediumint, SymbolId mediumint, the_raster text(200), intrasis_archive text(200), id int,PrimaryKey
geom (reader OGCGEOPACKAGE_4)
    attributes: ObjectId mediumint, MetaId mediumint, SymbolId mediumint, the_raster text(200), intrasis_archive text(200), id int,PrimaryKey
    -> GeometryFilter
GeometryFilter
    FILTER_MODE = SIMPLE
    FILTER_MULTI = FILTER_TYPES]Area]FME_CONTROLLER_QUERY_FILE]]FME_CONTROLLER_CHOICE]Simple
    Area -> Dissolver
Dissolver
    ACCUM_INPUT_ATTRS = Use Attributes From One Feature
    CLEANING_TOLERANCE = Automatic
    CONNECT_Z_MODE = First Wins
    DEAGGREGATE_INPUT = Yes
    DIS_ATTR = nuber_of_areas
    GROUP_BY = intrasis_archive
    AREA -> Aggregator
Aggregator
    ACCUM_ATTRS_NAME = Use Attributes From One Feature
    AGGREGATE_TYPE = Homogeneous Collection (If Possible)
    COUNT_ATTR = num_features
    GROUP_BY = intrasis_archive
    MODE = Geometry - Assemble One Level
    SEP = ,
    AGGREGATE -> BulkAttributeRenamer_3
BulkAttributeRenamer_3
    ATTRCHOICE = All Attributes
    MODE_CHOICE = RENAME
    PATTERN_ACTION_DISP = ADDPREFIX
    REPLACE_STR = geom_
    -> FeatureMerger [REQUESTOR]
new_MASTER (reader XLSXR_1)
    attributes: site_name char(54), site_archive char(17), uppdrag_nr number(10,0), kmr_uppdragsnummer number(10,0), UUID char(37), kmr_id char(37), Uppdaterat UUID char(37), Kommentar char(685), H char(4), J char(74)
    -> AttributeManager_5
AttributeManager_5
    ATTR_TABLE = SET_TO kmr_id = FME_CONDITIONAL:DEFAULT_VALUE'_FME_NO_OP_'BOOL_OP;OR;COMPOSITE_TEST;1;TEST Uppdaterat UUID ATTRIBUTE_HAS_A_VALUE _FME_BLANK_STRING_'@Value(Uppdaterat UUID)'FME_NUM_CONDITIONS2___
    -> BulkAttributeRenamer_2
BulkAttributeRenamer_2
    ATTRCHOICE = All Attributes
    MODE_CHOICE = RENAME
    PATTERN_ACTION_DISP = ADDPREFIX
    REPLACE_STR = master_
    -> FeatureMerger [SUPPLIER]
FeatureMerger
    ATTR_ACCUM_MODE = Merge Supplier
    ATTR_CONFLICT_RES = Use Requestor
    IGNORE_NULLS = No
    JOIN_KEYS = @Value(geom_intrasis_archive) @Value(master_site_archive) AUTO
    MERGE_TYPE = Attributes and Geometry
    PROCESS_DUPS = NO
    REJECT_NULL_MISSING_KEYS = No
    SUPPLIERS_FIRST = No
    MERGED -> AttributeRemover_2
AttributeRemover_2
    REMOVE_ATTRS = geom_MetaId,geom_nuber_of_areas,geom_num_features,geom_ObjectId,geom_SymbolId,geom_the_raster,master_H,master_J,master_site_archive,master_uppdrag_nr,master_UUID,master_Uppdaterat UUID
    -> SpatialRelator [Requestor]
sockenstad (reader OGCGEOPACKAGE_3)
    attributes: objektidentitet text(36), objektversion smallint, version_giltig_fran text(16), sockenstadkod text(4), sockenstadnamn text(100), sockenstadtyp smallint, omradesnummer smallint, huvudomrade text(1), sockenstadanmarkning text(254), OBJECTID int,PrimaryKey
    -> AttributeRemover

Bookmark: kommun
Kommun_Sweref99TM_region (reader SHAPEFILE_2)
    attributes: KnKod varchar(4), KnNamn varchar(15)
    -> SpatialRelator_2 [Supplier]
SpatialRelator_2
    AGGREGATE_HANDLING = Yes
    CALC_CARD = No
    CURVE_BOUNDARY_RULE_PARAM = Default Rule
    LIST_ATTRS_TO_INCLUDE = KnNamn
    LIST_NAME = _relationships
    PREDICATES = WITHIN CONTAINS INTERSECTS
    SUCCESS_ATTR = _kommun_antal
    -> ListConcatenator_2
ListConcatenator_2
    DROP_EMPTY_PARTS = No
    LIST_ATTR = _relationships{}.KnNamn
    SEP = ,
    VAL_ATTR = _kommun_concatenated
    -> AttributeManager_6
AttributeManager_6
    ATTR_TABLE:
      REMOVE _relationships{}.KnNamn
      REMOVE _relationships{}.de9im
      REMOVE _relationships{}.pass{}
    -> SpatialRelator_3 [Requestor]

Bookmark: kolla uo mot masyter
arkeologiska_uppdrag_undersökningsområden_sverige_polygon (reader OGCGEOPACKAGE_1)
    attributes: id text(255), uppdragsnummer text(9), beslutande_myndighet text(255), beslutsdatum date, diarienummer text(255), uppdragstyp text(255), utforande_organisation text(255), nollresultat text(9), url text(255), status text(255), lan text, kommun text, socken text, fid int,PrimaryKey
    -> BulkAttributeRenamer
arkeologiska_uppdrag_undersökningsområden_sverige_point (reader OGCGEOPACKAGE_1)
    attributes: id text(255), uppdragsnummer text(9), beslutande_myndighet text(255), beslutsdatum date, diarienummer text(255), uppdragstyp text(255), utforande_organisation text(255), nollresultat text(9), url text(255), status text(255), lan text, kommun text, socken text, fid int,PrimaryKey
    -> Bufferer_2
arkeologiska_uppdrag_undersökningsområden_sverige_linestring (reader OGCGEOPACKAGE_1)
    attributes: id text(255), uppdragsnummer text(9), beslutande_myndighet text(255), beslutsdatum date, diarienummer text(255), uppdragstyp text(255), utforande_organisation text(255), nollresultat text(9), url text(255), status text(255), lan text, kommun text, socken text, fid int,PrimaryKey
    -> Bufferer_2
Bufferer_2
    ANGLE = 22.5
    CAP_STYLE = Arc
    CORNER_STYLE = Arc
    MODE = AREA
    OFFSET = 500
    OFFSET_UNITS = METERS
    PRECISION = APPROX
    BUFFERED -> BulkAttributeRenamer
    <REJECTED> -> BulkAttributeRenamer
BulkAttributeRenamer
    ATTRCHOICE = All Attributes
    MODE_CHOICE = RENAME
    PATTERN_ACTION_DISP = ADDPREFIX
    REPLACE_STR = uom_
    -> SpatialRelator_5 [Supplier]
    -> FeatureMerger_4 [SUPPLIER]
SpatialRelator_5
    AGGREGATE_HANDLING = Yes
    CALC_CARD = No
    CURVE_BOUNDARY_RULE_PARAM = Default Rule
    LIST_ATTRS_TO_INCLUDE = uom_diarienummer uom_id
    LIST_NAME = _relationships
    PREDICATES = WITHIN CONTAINS INTERSECTS TOUCHES
    SUCCESS_ATTR = _uppdragsomraden_antal
    -> ListSearcher
ListSearcher
    ATTR_VALUE = @Value(master_kmr_id)
    CASE = CASE_SENSITIVE
    INDEX_ATTR = _list_index
    LIST_ATTR = _relationships{}.uom_id
    MATCHTYPE = FIRST_MATCHED_ENCODED
    FOUND -> AttributeManager_2
    NOT_FOUND -> AttributeManager_7
AttributeManager_2
    ATTR_TABLE:
      REMOVE _relationships{}.uom_id
      REMOVE _relationships{}.uom_diarienummer
      REMOVE _relationships{}.de9im
      REMOVE _relationships{}.pass{}
      SET_TO kmr_id_traff_i_uom = true
    -> FeatureMerger_4 [REQUESTOR]
FeatureMerger_4
    ATTR_ACCUM_MODE = Merge Supplier
    ATTR_CONFLICT_RES = Use Requestor
    IGNORE_NULLS = No
    JOIN_KEYS = @Value(master_kmr_uppdragsnummer) @Value(uom_uppdragsnummer) AUTO
    MERGE_TYPE = Attributes Only
    PROCESS_DUPS = NO
    REJECT_NULL_MISSING_KEYS = No
    SUPPLIERS_FIRST = No
    MERGED -> FeatureMerger_2 [SUPPLIER]
    UNMERGED_REQUESTOR -> FeatureMerger_2 [SUPPLIER]
AttributeManager_7
    ATTR_TABLE:
      REMOVE _relationships{}.uom_id
      REMOVE _relationships{}.uom_diarienummer
      REMOVE _relationships{}.de9im
      REMOVE _relationships{}.pass{}
      SET_TO kmr_id_traff_i_uom = false
    -> FeatureMerger_2 [SUPPLIER]
FeatureMerger_2
    ATTR_ACCUM_MODE = Merge Supplier
    ATTR_CONFLICT_RES = Use Requestor
    IGNORE_NULLS = No
    JOIN_KEYS = @Value(geom_intrasis_archive) @Value(geom_intrasis_archive) AUTO
    MERGE_TYPE = Attributes Only
    PROCESS_DUPS = NO
    REJECT_NULL_MISSING_KEYS = No
    SUPPLIERS_FIRST = No
    MERGED -> GeometryRemover

Bookmark: socken
AttributeRemover
    REMOVE_ATTRS = huvudomrade,OBJECTID,objektidentitet,objektversion,omradesnummer,sockenstadanmarkning,version_giltig_fran
    -> SpatialRelator [Supplier]
SpatialRelator
    AGGREGATE_HANDLING = Yes
    CALC_CARD = No
    CURVE_BOUNDARY_RULE_PARAM = Default Rule
    LIST_ATTRS_TO_INCLUDE = sockenstadnamn
    LIST_NAME = _relationships
    PREDICATES = WITHIN CONTAINS INTERSECTS
    SUCCESS_ATTR = _socken_antal
    -> ListConcatenator
ListConcatenator
    DROP_EMPTY_PARTS = No
    LIST_ATTR = _relationships{}.sockenstadnamn
    SEP = " , "
    VAL_ATTR = _socken_concatenated
    -> AttributeManager
AttributeManager
    ATTR_TABLE:
      REMOVE _relationships{}.sockenstadnamn
      REMOVE _relationships{}.de9im
      REMOVE _relationships{}.pass{}
    -> SpatialRelator_2 [Requestor]

Bookmark: lan
Lan_Sweref99TM_region (reader SHAPEFILE_3)
    attributes: LnKod varchar(2), LnNamn varchar(20)
    -> SpatialRelator_3 [Supplier]
SpatialRelator_3
    AGGREGATE_HANDLING = Yes
    CALC_CARD = No
    CURVE_BOUNDARY_RULE_PARAM = Default Rule
    LIST_ATTRS_TO_INCLUDE = LnNamn
    LIST_NAME = _relationships
    PREDICATES = WITHIN CONTAINS INTERSECTS
    SUCCESS_ATTR = _lan_antal
    -> ListConcatenator_3
ListConcatenator_3
    DROP_EMPTY_PARTS = No
    LIST_ATTR = _relationships{}.LnNamn
    SEP = " , "
    VAL_ATTR = lan_concatenated
    -> AttributeManager_3
AttributeManager_3
    ATTR_TABLE:
      RENAME_SET_VALUE lan_concatenated > _lan_concatenated
      REMOVE _relationships{}.LnNamn
      REMOVE _relationships{}.de9im
      REMOVE _relationships{}.pass{}
    -> SpatialRelator_4 [Requestor]

Bookmark: Landskap
svelandskap_2010_rev_granser (reader SHAPEFILE_1)
    attributes: LANDSKAP varchar(254), ID number(16,0), KOMMENTAR varchar(150), SKALA varchar(100), AREA_METER double, PERIMETER_ double, HECTARES double
    -> SpatialRelator_4 [Supplier]
SpatialRelator_4
    AGGREGATE_HANDLING = Yes
    CALC_CARD = No
    CURVE_BOUNDARY_RULE_PARAM = Default Rule
    LIST_ATTRS_TO_INCLUDE = LANDSKAP
    LIST_NAME = _relationships
    PREDICATES = WITHIN CONTAINS INTERSECTS
    SUCCESS_ATTR = _landskap_antal
    -> ListConcatenator_4
ListConcatenator_4
    DROP_EMPTY_PARTS = No
    LIST_ATTR = _relationships{}.LANDSKAP
    SEP = " , "
    VAL_ATTR = _landskap_concatanted
    -> AttributeManager_4
AttributeManager_4
    ATTR_TABLE:
      REMOVE _relationships{}.de9im
      REMOVE _relationships{}.pass{}
      REMOVE _relationships{}.LANDSKAP
    -> SpatialRelator_5 [Requestor]
    -> FeatureMerger_2 [REQUESTOR]
