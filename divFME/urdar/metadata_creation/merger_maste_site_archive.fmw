FME workspace merger_maste_site_archive.fmw

Parameters:
- SourceDataset_OGCGEOPACKAGE = C:\Users\krima354\Work Folders\Documents\kicki_arbetsfiler\slask\all_intrasisArchive_20231213_5.gpkg   # GeoPackage File
- SourceDataset_OGCGEOPACKAGE_3 = C:\Users\krima354\Box\Urdar\uuid_check\intrasis_archive_UUID_master.gpkg   # GeoPackage File

Readers:
- OGCGEOPACKAGE_1: OGCGEOPACKAGE from $(SourceDataset_OGCGEOPACKAGE) in EPSG:3006
- OGCGEOPACKAGE_2: OGCGEOPACKAGE from $(SourceDataset_OGCGEOPACKAGE_3) in EPSG:3006

UUID_master_final20231212 (reader OGCGEOPACKAGE_2)
    attributes: intrasisarchive text(200), pk mediumint, SiteId text, Plats text, Lst Dnr text, Raä Dnr text, Inventarienummer text, Projektkod text, Projektnamn text, Projektledare text, Uppdragsgivare text, Exploateringstyp text, Undersökningstyp text, Slutdatum text, Beskrivning text, fid int, id int, lage text(200), numOfFeature int, geom_intrasisarchive text(200), agg_feat int, UUID_kix text(200), master_site_name text(54), master_site_archive text(17), master_uppdrag_nr int, master_kmr_uppdragsnummer int, master_UUID text(37), master_kmr_id text(37), master_Uppdaterat UUID text(37), master_Kommentar text(685),
      master_H text(4), master_col9 text(74), master__length_uppdrag_nr text(20), link_fornsok text(200), master_uppdrag_ny text(200), _relationships.undersokningsomraden_id text, _relationships.de9im text, _relationships.pass text, _related_suppliers int, ok_kix text(200), project_info_intrasisarchive text(200), project_info_pk mediumint, project_info_SiteId text, project_info_Plats text, project_info_Lst Dnr text, project_info_Raä Dnr text, project_info_Inventarienummer text, project_info_Projektkod text, project_info_Projektnamn text, project_info_Projektledare text, project_info_Uppdragsgivare text, project_info_Exploateringstyp text, project_info_Undersökningstyp text, project_info_Slutdatum text, project_info_Beskrivning text, project_info_fid int, project_info_id int, Geoobjekt_manuellt_georefererade mediumint, Georeferering_precision text(200), datname text,
      type_kix text(200), _traff_med_uo_id text, traff_undersokningsomraden_id text(255), traff_de9im text, traff_pass text, _list_index int, id_0 int,PrimaryKey
    -> FeatureMerger [REQUESTOR]
siteinfo_concat_2 (reader OGCGEOPACKAGE_1)
    attributes: intrasis_archive text(200), _id_fr_upp text, _kommun text, _kommun_fr_upp text, _lan text, _lan_fr_upp text, _landskap text, _socken_stad text, _socken_fr_upp text, _diarienummer_fr_upp text, _beslutande_myndighet_fr_upp text, _uppdragsnummer_fr_upp text, _utförande_org_fr_upp text, id int,PrimaryKey
    -> FeatureMerger [SUPPLIER]
FeatureMerger
    ATTR_ACCUM_MODE = Merge Supplier
    ATTR_CONFLICT_RES = Use Requestor
    IGNORE_NULLS = No
    JOIN_KEYS = @Value(master_site_archive) @Value(intrasis_archive) AUTO
    MERGE_TYPE = Attributes and Geometry
    PROCESS_DUPS = NO
    REJECT_NULL_MISSING_KEYS = No
    SUPPLIERS_FIRST = No
    MERGED -> AttributeManager
    UNMERGED_REQUESTOR -> AttributeManager
AttributeManager
    ATTR_TABLE:
      REMOVE geom_intrasisarchive
      REMOVE project_info_intrasisarchive
      REMOVE intrasis_archive
      REMOVE intrasisarchive
      REMOVE fid
      REMOVE id
    -> TestFilter
TestFilter
    DEFAULT_VALUE = <UNFILTERED>
    PASSED_TEST_GROUP_OUTPUT = FIRST
    TEST_LIST:
      "BOOL_OP,AND,COMPOSITE_TEST,""""""1 AND 2 AND 3 AND 4 AND 5 AND 6 AND 7 AND 8"""""",TEST_CLAUSE,TEST @Value(project_info_Lst Dnr) = @Value(Lst Dnr)
      TEST @Value(project_info_Projektledare) = @Value(Projektledare)
      TEST @Value(Projektkod) = @Value(project_info_Projektkod)
      TEST @Value(Projektnamn) = @Value(project_info_Projektnamn)
      TEST @Value(SiteId) = @Value(project_info_SiteId)
      TEST @Value(Slutdatum) = @Value(project_info_Slutdatum)
      TEST @Value(Undersökningstyp) = @Value(project_info_Undersökningstyp)
      TEST @Value(Uppdragsgivare) = @Value(project_info_Uppdragsgivare)",@Value(project_info_Lst Dnr) = @Value(Lst Dnr)
    <UNFILTERED> -> AttributeManager_2
    @Value(project_info_Lst Dnr) = @Value(Lst Dnr) -> AttributeManager_3
medianpoint (reader OGCGEOPACKAGE_1)
    attributes: intrasis_archive text(200), ObjectId mediumint, MetaId mediumint, SymbolId mediumint, the_raster text(200), _inside_x double, _inside_y double, _inside_z double, id int,PrimaryKey
all_intrasisarchive_geom (reader OGCGEOPACKAGE_1)
    attributes: ObjectId mediumint, MetaId mediumint, SymbolId mediumint, the_raster text(200), intrasis_archive text(200), id int,PrimaryKey
siteinfo_2 (reader OGCGEOPACKAGE_1)
    attributes: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
AttributeRemover [off]
    REMOVE_ATTRS = Beskrivning,Exploateringstyp,Geoobjekt_manuellt_georefererade,Georeferering_precision,Inventarienummer,Plats,UUID_kix,_beslutande_myndighet_fr_upp,_diarienummer_fr_upp,_id_fr_upp,_kommun,_kommun_fr_upp,_lan,_lan_fr_upp,_landskap,_list_index,_related_suppliers,_relationships.de9im,_relationships.pass,_relationships.undersokningsomraden_id,_socken_fr_upp,_socken_stad,_traff_med_uo_id,_uppdragsnummer_fr_upp,_utförande_org_fr_upp,agg_feat,datname,id_0,lage,link_fornsok,master_H,master_Kommentar,master_UUID,master_Uppdaterat UUID,master__length_uppdrag_nr,master_col9,master_kmr_id,master_kmr_uppdragsnummer,master_site_name,master_uppdrag_nr,master_uppdrag_ny,numOfFeature,ok_kix,pk,project_info_Inventarienummer,project_info_Plats,project_info_fid,project_info_id,project_info_pk,traff_de9im,traff_pass,traff_undersokningsomraden_id
    -> AttributeManager_2
AttributeManager_2
    ATTR_TABLE:
      SET_TO project_info_Lst Dnr = @Value(Lst Dnr)
      SET_TO project_info_Projektnamn = @Value(Projektledare)
      SET_TO project_info_Uppdragsgivare = @Value(Uppdragsgivare)
      SET_TO project_info_Undersökningstyp = @Value(Undersökningstyp)
      SET_TO project_info_Slutdatum = @Value(Slutdatum)
    -> AttributeManager_3
AttributeManager_3
    ATTR_TABLE:
      REMOVE Raä Dnr
      REMOVE Projektkod
      REMOVE Projektnamn
      REMOVE Projektledare
      REMOVE Uppdragsgivare
      REMOVE Undersökningstyp
      REMOVE Slutdatum
      REMOVE pk
      REMOVE Plats
      REMOVE id_0
      REMOVE Inventarienummer
      REMOVE Exploateringstyp
      REMOVE Beskrivning
      REMOVE lage
      REMOVE numOfFeature
      REMOVE _relationships.undersokningsomraden_id
      REMOVE _relationships.de9im
      REMOVE _relationships.pass
      REMOVE _related_suppliers
      REMOVE agg_feat
      REMOVE link_fornsok
      REMOVE SiteId
      REMOVE traff_de9im
      REMOVE traff_pass
      REMOVE _list_index
      REMOVE _id_fr_upp
      REMOVE master_H
      REMOVE master_col9
    -> TestFilter_2
TestFilter_2
    DEFAULT_VALUE = <UNFILTERED>
    PASSED_TEST_GROUP_OUTPUT = FIRST
    TEST_LIST = "BOOL_OP,OR,COMPOSITE_TEST,""""""1"""""",TEST_CLAUSE,TEST @Value(UUID_kix) = @Value(master_UUID)",@Value(UUID_kix) = @Value(master_UUID),"BOOL_OP,OR,COMPOSITE_TEST,""""""1"""""",TEST_CLAUSE,TEST @Value(UUID_kix) = @Value(master_Uppdaterat UUID)",master_Uppdaterat UUID
    <UNFILTERED> -> AttributeManager_5
    @Value(UUID_kix) = @Value(master_UUID) -> AttributeManager_4
    master_Uppdaterat UUID -> AttributeManager_4
AttributeManager_4
    ATTR_TABLE = SET_TO UUID_kix
    -> AttributeManager_6
AttributeManager_5
    -> AttributeManager_6
AttributeManager_6
    ATTR_TABLE = RENAME_SET_VALUE UUID_kix > UUID_andrat_av_uu
    -> SpatialFilter [Candidate]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS CONTAINS
    USE_BOUNDING_BOX = No
    FAILED -> GeometryFilter
GeometryFilter
    FILTER_MODE = SIMPLE
    FILTER_MULTI = FILTER_TYPES]Null]FME_CONTROLLER_QUERY_FILE]]FME_CONTROLLER_CHOICE]Simple
    <UNFILTERED> -> TestFilter_3
TestFilter_3
    DEFAULT_VALUE = <UNFILTERED>
    PASSED_TEST_GROUP_OUTPUT = FIRST
    TEST_LIST = "BOOL_OP,OR,COMPOSITE_TEST,""""""1"""""",TEST_CLAUSE,CASE_INSENSITIVE_TEST @Value(master_site_archive) BEGINS_WITH e",extern

Bookmark: 3006 bounds
Creator
    GEOMTYPE = Geometry Object
    NUM = 1
    CREATED -> EPSG:3006
EPSG:3006: AttributeManager
    ATTR_TABLE:
      SET_TO miny = 6090353.78
      SET_TO minx = 181896.33
      SET_TO maxy = 7689478.31
      SET_TO maxx = 1086312.94
    -> VertexCreator_2
VertexCreator_2
    CLOSE_LINES = Yes
    IGNORE_DUPLICATES = No
    MEASURE_TYPE = Continuous
    MISSING_VAL_MODE = Compute
    MODE_NAME = Add Point
    XVAL = @Value(minx)
    YVAL = @Value(miny)
    -> VertexCreator_3
VertexCreator_3
    CLOSE_LINES = Yes
    IGNORE_DUPLICATES = No
    MEASURE_TYPE = Continuous
    MISSING_VAL_MODE = Compute
    MODE_NAME = Add Point
    XVAL = @Value(maxx)
    YVAL = @Value(miny)
    -> VertexCreator
VertexCreator
    CLOSE_LINES = Yes
    IGNORE_DUPLICATES = No
    MEASURE_TYPE = Continuous
    MISSING_VAL_MODE = Compute
    MODE_NAME = Add Point
    XVAL = @Value(maxx)
    YVAL = @Value(maxy)
    -> VertexCreator_4
VertexCreator_4
    CLOSE_LINES = Yes
    IGNORE_DUPLICATES = No
    MEASURE_TYPE = Continuous
    MISSING_VAL_MODE = Compute
    MODE_NAME = Add Point
    XVAL = @Value(minx)
    YVAL = @Value(maxy)
    -> VertexCreator_5
VertexCreator_5
    CLOSE_LINES = Yes
    IGNORE_DUPLICATES = No
    MEASURE_TYPE = Continuous
    MISSING_VAL_MODE = Compute
    MODE_NAME = Add Point
    XVAL = @Value(minx)
    YVAL = @Value(miny)
    -> SpatialFilter [Filter]
