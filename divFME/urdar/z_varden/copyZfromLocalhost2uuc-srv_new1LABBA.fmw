FME workspace copyZfromLocalhost2uuc-srv_new1LABBA.fmw

Parameters:
- SourceDataset_POSTGIS_3 = masterby_2010   # Database

Readers:
- POSTGIS_1: POSTGIS from $(SourceDataset_POSTGIS_3)
- POSTGIS_2: POSTGIS from $(SourceDataset_POSTGIS_3)

Writers:
- POSTGIS_3: POSTGIS to $(SourceDataset_POSTGIS_3) in EPSG:3006

Note: uuc-srv
GeoObject (reader POSTGIS_2)
    attributes: ObjectId int4, MetaId int4, SymbolId int4, the_raster raster
    -> MeasureRemover
MeasureRemover
    REMOVE_ALL = Yes
    -> 2DForcer
2DForcer
    2D -> FeatureMerger [REQUESTOR]
Note: localhost
GeoObject (reader POSTGIS_1)
    attributes: ObjectId int4, MetaId int4, SymbolId int4, the_raster raster
    -> GeometryExtractor
GeometryExtractor
    ATTR = _geometry
    KIND_LONG = OGC Well Known Text
    OGCVERSION = 1.2
    OGC_WKT_PRECISION_DISPLAY = 64-bit
    REMOVE_GEOMETRY = No
    -> CoordinateExtractor_3
CoordinateExtractor_3
    LIST_NAME = _localhost
    MODE = All Coordinates
    -> FeatureMerger [SUPPLIER]
FeatureMerger
    ATTR_ACCUM_MODE = Merge Supplier
    ATTR_CONFLICT_RES = Use Requestor
    IGNORE_NULLS = No
    JOIN_KEYS = @Value(ObjectId) @Value(ObjectId) AUTO
    MERGE_TYPE = Attributes Only
    PROCESS_DUPS = NO
    REJECT_NULL_MISSING_KEYS = No
    SUPPLIERS_FIRST = No
    MERGED -> GeometryFilter
GeometryFilter
    FILTER_MODE = COMPLETE
    FILTER_MULTI = FILTER_TYPES]"Area Donut SimpleArea Polygon MultiArea MultiPoint Point Curve Line"]INSTANCES]INSTANCE]FME_CONTROLLER_QUERY_FILE]]FME_CONTROLLER_CHOICE]Complete
    Point -> GeometryExtractor_2
    MultiPoint -> GeometryExtractor_2
    Curve -> GeometryExtractor_2
    Line -> GeometryExtractor_2
    Area -> GeometryExtractor_2
    SimpleArea -> GeometryExtractor_2
    Polygon -> GeometryExtractor_2
    Donut -> GeometryExtractor_2
    MultiArea -> GeometryExtractor_2
    <UNFILTERED> -> GeometryExtractor_2
GeometryExtractor_2
    ATTR = _geometry
    KIND_LONG = OGC Well Known Text
    OGCVERSION = 1.2
    OGC_WKT_PRECISION_DISPLAY = 64-bit
    REMOVE_GEOMETRY = No
    -> ListElementCounter
ListElementCounter
    CNT_ATTR = _element_count
    LIST_NAME = _localhost{}
    -> ListConcatenator
ListConcatenator
    DROP_EMPTY_PARTS = No
    LIST_ATTR = _localhost{}.z
    SEP = " , "
    VAL_ATTR = _concatenated
    -> 3DForcer_2
3DForcer_2
    KEEPZVAL = No
    ZVALATTR = 0
    -> GeometryExtractor_3
GeometryExtractor_3
    ATTR = _geometry
    KIND_LONG = OGC Well Known Text
    OGCVERSION = 1.2
    OGC_WKT_PRECISION_DISPLAY = 64-bit
    REMOVE_GEOMETRY = No
    -> PythonCaller
Note: replace 0
PythonCaller
    PYTHONSOURCE:
      import fme
      import fmeobjects


      class FeatureProcessor(object):
          """Template Class Interface:
          When using this class, make sure its name is set as the value of the 'Class
          to Process Features' transformer parameter.
          """

          def __init__(self):
              """Base constructor for class members."""
              pass

          def input(self, feature):
              """This method is called for each FME Feature entering the
              PythonCaller. If knowledge of all input Features is not required for
              processing, then the processed Feature can be emitted from this method
              through self.pyoutput(). Otherwise, the input FME Feature should be
              cached to a list class member and processed in process_group() when
              'Group by' attributes(s) are specified, or the close() method.

              :param fmeobjects.FMEFeature feature: FME Feature entering the
                  transformer.
              """
              my_list = feature.getAttribute('_localhost{}.z')
              geom_string = feature.getAttribute('_geometry')
              '''
              found= geom_string.find("GEOMETRYCOLLECTION")
              if (found > -1 ):
                  geom_string = geom_string.replace("GEOMETRYCOLLECTION Z (", "",1)
                  geom_string = geom_string[:-1]
              '''
              lastIndex = len(my_list)
              num=1

              for item in my_list:
                  geom_string = geom_string.replace(" 0" ," " + f"{item}" ,1)

              #feature.setAttribute('lastIndex', lastIndex)
              #feature.setAttribute('numIterations', num)
              feature.setAttribute('_geometry', geom_string)
              self.pyoutput(feature)

          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> GeometryReplacer_2
GeometryReplacer_2
    KIND_LONG = OGC Well Known Text
    OGC_WKT_PRECISION_DISPLAY = 64-bit
    REMOVE_ATTRIBUTE = No
    SOURCE = @Value(_geometry)
    -> GeoObject (writer POSTGIS_3)
GeoObject (writer POSTGIS_3)
    attributes: ObjectId int4, MetaId int4, SymbolId int4
FeatureMerger_2
    ATTR_ACCUM_MODE = Merge Supplier
    ATTR_CONFLICT_RES = Use Requestor
    IGNORE_NULLS = No
    JOIN_KEYS = @Value(ObjectId) @Value(ObjectId) AUTO
    MERGE_TYPE = Attributes Only
    PROCESS_DUPS = NO
    REJECT_NULL_MISSING_KEYS = No
    SUPPLIERS_FIRST = No
FMEFunctionCaller_3 [off]
    FUNC = @ZValue(_localhost{}.z)

Bookmark: remove m
MeasureRemover_3
    REMOVE_ALL = Yes
MeasureRemover_4
    REMOVE_ALL = Yes
