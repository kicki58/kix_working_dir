FME workspace testing20230920_3.fmw

Parameters:
- SourceDataset_OGCGEOPACKAGE = C:\Users\krima354\Work Folders\Documents\kicki_arbetsfiler\urdar_arbetsfiler\allaIntrasisArchive_sridCheck6.gpkg   # GeoPackage File
- SourceDataset_CSV2 = C:\Users\krima354\Work Folders\Documents\kicki_arbetsfiler\urdar_arbetsfiler\UUID MASTER 20221007.csv   # Source CSV (Comma Separated Value) File(s)
- SourceDataset_OGCGEOPACKAGE_7 = C:\Users\krima354\Work Folders\Documents\kicki_arbetsfiler\urdar_arbetsfiler\arkeologiska_uppdrag_grävda_ytor_sverige.gpkg   # GeoPackage File
- SourceDataset_OGCGEOPACKAGE_5 = C:\Users\krima354\Work Folders\Documents\kicki_arbetsfiler\urdar_arbetsfiler\arkeologiska_uppdrag_undersökningsområden_sverige.gpkg   # GeoPackage File
- SourceDataset_OGCGEOPACKAGE_6 = C:\Users\krima354\Work Folders\Documents\kicki_arbetsfiler\urdar_arbetsfiler\allaIntrasisArchive6.gpkg   # GeoPackage File
- DestDataset_OGCGEOPACKAGE = C:\Users\krima354\Box\Urdar\uuid_check\intrasis_archive_UUID_master.gpkg   # GeoPackage File

Readers:
- OGCGEOPACKAGE_1: OGCGEOPACKAGE from $(SourceDataset_OGCGEOPACKAGE) in EPSG:3006
- CSV2_1: CSV2 from $(SourceDataset_CSV2)
- OGCGEOPACKAGE_2: OGCGEOPACKAGE from $(SourceDataset_OGCGEOPACKAGE_7) in EPSG:3006
- OGCGEOPACKAGE_3: OGCGEOPACKAGE from $(SourceDataset_OGCGEOPACKAGE_5) in EPSG:3006
- OGCGEOPACKAGE_4: OGCGEOPACKAGE from $(SourceDataset_OGCGEOPACKAGE_6) in EPSG:3006

Writers:
- OGCGEOPACKAGE_5: OGCGEOPACKAGE to $(DestDataset_OGCGEOPACKAGE)

CSV (reader CSV2_1)
    attributes: site_name varchar(54), site_archive varchar(17), uppdrag_nr uint32, kmr_uppdragsnummer uint32, UUID varchar(37), kmr_id varchar(37), Uppdaterat UUID varchar(37), Kommentar varchar(685), H varchar(4), col9 varchar(74)
    -> StringLengthCalculator
StringLengthCalculator
    LENGTH_ATTR = _length_uppdrag_nr
    SRC_ATTR = uppdrag_nr
    -> BulkAttributeRenamer
BulkAttributeRenamer
    ATTRCHOICE = All Attributes
    MODE_CHOICE = RENAME
    PATTERN_ACTION_DISP = ADDPREFIX
    REPLACE_STR = master_
    -> AttributeManager
AttributeManager
    ATTR_TABLE:
      SET_TO UUID_kix = FME_CONDITIONAL:DEFAULT_VALUE'_FME_NO_OP_'BOOL_OP;OR;COMPOSITE_TEST;1;TEST master_Uppdaterat UUID ATTRIBUTE_HAS_A_VALUE _FME_BLANK_STRING_'@Value(master_Uppdaterat UUID)'BOOL_OP;OR;COMPOSITE_TEST;1;TEST @Value(master_UUID) = @Value(master_kmr_id)'@Value(master_UUID)'BOOL_OP;OR;COMPOSITE_TEST;1;TEST master_UUID ATTRIBUTE_HAS_A_VALUE _FME_BLANK_STRING_'@Value(master_UUID)'FME_NUM_CONDITIONS4___
      SET_TO link_fornsok = https://app.raa.se/open/fornsok/uppdrag/@Value(UUID_kix)
      SET_TO master_uppdrag_ny = FME_CONDITIONAL:DEFAULT_VALUE'@Value(master_uppdrag_nr)'BOOL_OP;OR;COMPOSITE_TEST;1;CASE_INSENSITIVE_TEST @Value(master_uppdrag_nr) BEGINS_WITH 1'000@Value(master_uppdrag_nr)'FME_NUM_CONDITIONS2___
    -> FeatureMerger_4 [REQUESTOR]
project_information (reader OGCGEOPACKAGE_4)
    attributes: intrasisarchive text(200), pk mediumint, SiteId text, Plats text, Lst Dnr text, Raä Dnr text, Inventarienummer text, Projektkod text, Projektnamn text, Projektledare text, Uppdragsgivare text, Exploateringstyp text, Undersökningstyp text, Slutdatum text, Beskrivning text, fid int, id int,PrimaryKey
    -> BulkAttributeRenamer_2
    -> FeatureMerger [REQUESTOR]
    -> FeatureMerger_5 [REQUESTOR]
    -> FeatureMerger_6 [REQUESTOR]
BulkAttributeRenamer_2
    ATTRCHOICE = All Attributes
    MODE_CHOICE = RENAME
    PATTERN_ACTION_DISP = ADDPREFIX
    REPLACE_STR = project_info_
    -> FeatureMerger_4 [SUPPLIER]
FeatureMerger_4
    ATTR_ACCUM_MODE = Merge Supplier
    ATTR_CONFLICT_RES = Use Requestor
    IGNORE_NULLS = No
    JOIN_KEYS = @Value(master_site_archive) @Value(project_info_intrasisarchive) AUTO
    MERGE_TYPE = Attributes Only
    PROCESS_DUPS = NO
    REJECT_NULL_MISSING_KEYS = No
    SUPPLIERS_FIRST = No
    MERGED -> FeatureMerger_2 [SUPPLIER]
geom (reader OGCGEOPACKAGE_4)
    attributes: intrasisarchive text(200), fid int, IntrasisId int, object_id mediumint, Name text, Class text, SubClass text, SymbolId mediumint, GeoObjectId mediumint, spatial_type text, id int,PrimaryKey
    -> BulkAttributeRenamer_5
BulkAttributeRenamer_5
    ATTRCHOICE = All Attributes
    MODE_CHOICE = RENAME
    PATTERN_ACTION_DISP = ADDPREFIX
    REPLACE_STR = geom_
    -> Aggregator_2
Aggregator_2
    ACCUM_ATTRS_NAME = Drop Incoming Attributes
    AGGREGATE_TYPE = Homogeneous Collection (If Possible)
    COUNT_ATTR = agg_feat
    GROUP_BY = geom_intrasisarchive
    MODE = Geometry - Assemble One Level
    SEP = ,
    AGGREGATE -> FeatureMerger_2 [REQUESTOR]
FeatureMerger_2
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = @Value(geom_intrasisarchive) @Value(master_site_archive) AUTO
    MERGE_TYPE = Attributes Only
    PROCESS_DUPS = YES
    REJECT_NULL_MISSING_KEYS = No
    SUPPLIERS_FIRST = No
    MERGED -> SpatialRelator [Requestor]
SpatialRelator
    AGGREGATE_HANDLING = Yes
    CALC_CARD = No
    CURVE_BOUNDARY_RULE_PARAM = Default Rule
    LIST_ATTRS_TO_INCLUDE = undersokningsomraden_id
    LIST_NAME = _relationships
    PREDICATES = WITHIN INTERSECTS TOUCHES
    SUCCESS_ATTR = _related_suppliers
    -> ListSearcher
Note: proj_info geometri finns inom uo- geometri / not_founf- har ett UUID som finns i uo men proj_info geometrin finns ej i närheten
ListSearcher
    ATTR_VALUE = @Value(UUID_kix)
    CASE = CASE_SENSITIVE
    INDEX_ATTR = _list_index
    LIST_ATTR = _relationships{}.undersokningsomraden_id
    MATCHTYPE = FIRST_MATCHED_ENCODED
    PREFIX = traff_
    FOUND -> FeatureMerger_6 [SUPPLIER]
    NOT_FOUND -> AttributeManager_2
FeatureMerger_6
    ATTR_ACCUM_MODE = Merge Supplier
    ATTR_CONFLICT_RES = Use Requestor
    IGNORE_NULLS = No
    JOIN_KEYS = @Value(intrasisarchive) @Value(master_site_archive) AUTO
    MERGE_TYPE = Attributes Only
    PROCESS_DUPS = NO
    REJECT_NULL_MISSING_KEYS = No
    SUPPLIERS_FIRST = No
    MERGED -> archives_uuid_found_stickprov (writer OGCGEOPACKAGE_5)
archives_uuid_found_stickprov (writer OGCGEOPACKAGE_5)
    attributes: geom_intrasisarchive text(200), agg_feat int, UUID_kix text(200), master_site_name text(54), master_site_archive text(17), master_uppdrag_nr int, master_kmr_uppdragsnummer int, master_UUID text(37), master_kmr_id text(37), master_Uppdaterat UUID text(37), master_Kommentar text(685), master_H text(4), master_col9 text(74), master__length_uppdrag_nr text(20), link_fornsok text(200), master_uppdrag_ny text(200), project_info_intrasisarchive text(200), project_info_pk mediumint, project_info_SiteId text, project_info_Plats text, project_info_Lst Dnr text, project_info_Raä Dnr text, project_info_Inventarienummer text, project_info_Projektkod text, project_info_Projektnamn text, project_info_Projektledare text, project_info_Uppdragsgivare text, project_info_Exploateringstyp text, project_info_Undersökningstyp text, project_info_Slutdatum text,
      project_info_Beskrivning text, project_info_fid int, project_info_id int,PrimaryKey, _relationships{}.undersokningsomraden_id text(255), _relationships{}.de9im text, _relationships{}.pass{} text, _related_suppliers int, traff_undersokningsomraden_id text(255), traff_de9im text, traff_pass{} text, _list_index int, intrasisarchive text(200), pk mediumint, SiteId text, Plats text, Lst Dnr text, Raä Dnr text, Inventarienummer text, Projektkod text, Projektnamn text, Projektledare text, Uppdragsgivare text, Exploateringstyp text, Undersökningstyp text, Slutdatum text, Beskrivning text, fid int, id int
AttributeManager_2
    ATTR_TABLE = SET_TO ok_kix
    -> FeatureMerger_3 [REQUESTOR]
Note: tar bort alla utanför 3006 / att kolla upp merged
FeatureMerger_3
    ATTR_ACCUM_MODE = Merge Supplier
    ATTR_CONFLICT_RES = Use Requestor
    IGNORE_NULLS = No
    JOIN_KEYS = @Value(master_site_archive) @Value(intrasisarchive) AUTO
    MERGE_TYPE = Attributes Only
    PROCESS_DUPS = NO
    REJECT_NULL_MISSING_KEYS = No
    SUPPLIERS_FIRST = No
    MERGED -> TestFilter
    MERGED -> GeometryRemover
    UNMERGED_REQUESTOR -> ListConcatenator
    UNUSED_SUPPLIER -> GeometryRemover
TestFilter
    DEFAULT_VALUE = <UNFILTERED>
    PASSED_TEST_GROUP_OUTPUT = FIRST
    TEST_LIST:
      "BOOL_OP,OR,COMPOSITE_TEST,""""""1 OR 2"""""",TEST_CLAUSE,CASE_INSENSITIVE_TEST @Value(master_site_name) LIKE Kleopatra
      CASE_INSENSITIVE_TEST @Value(master_site_name) LIKE Single-surface",Västerås?,"BOOL_OP,OR,COMPOSITE_TEST,""""""1"""""",TEST_CLAUSE,TEST @Value(master_site_name) = Kongens Nytorv",Köpenhamn?,"BOOL_OP,OR,COMPOSITE_TEST,""""""1"""""",TEST_CLAUSE,TEST @Value(master_site_name) = Uppåkra proj. Metalldet.",Malmö?,"BOOL_OP,OR,COMPOSITE_TEST,""""""1"""""",TEST_CLAUSE,TEST @Value(master_site_name) = Aranäsprojektet",Aranäs-gbg?,"BOOL_OP,OR,COMPOSITE_TEST,""""""1"""""",TEST_CLAUSE,TEST @Value(master_site_name) = Monte Polizzo",Malta,"BOOL_OP,OR,COMPOSITE_TEST,""""""1 OR 2"""""",TEST_CLAUSE,TEST @Value(master_site_name) = Brandstationen 7 slut
      TEST @Value(master_site_name) = Alberts Gärde",Örebro?,"BOOL_OP,OR,COMPOSITE_TEST,""""""1"""""",TEST_CLAUSE,TEST @Value(master_site_name) = Arboga Koberg",Arbåga,"BOOL_OP,OR,COMPOSITE_TEST,""""""1 OR 2 OR 3"""""",TEST_CLAUSE,TEST @Value(master_site_name) = Hassle
      TEST @Value(master_site_name) = Svärdbäraren
      TEST @Value(master_site_name) = Den medeltida borgen Kärnan",Löst koord,"BOOL_OP,OR,COMPOSITE_TEST,""""""1 OR 2 OR 3 OR 4 OR 5 OR 6 OR 7"""""",TEST_CLAUSE,TEST @Value(master_site_name) = Rudbeck schaktöver
      TEST @Value(master_site_name) = Källargränd FU
      TEST @Value(master_site_name) = Käringsjön
      TEST @Value(master_site_name) = Fristad Paradis UTR
      TEST @Value(master_site_name) = St.Peder 56
      TEST @Value(master_site_name) = Älvsåker 15:1
      TEST @Value(master_site_name) = Hanhals 136",Vet ej,"BOOL_OP,OR,COMPOSITE_TEST,""""""1"""""",TEST_CLAUSE,TEST @Value(master_site_name) = Lännäs FU",Lännäs, närke,"BOOL_OP,OR,COMPOSITE_TEST,""""""1"""""",TEST_CLAUSE,CASE_INSENSITIVE_TEST @Value(master_site_name) CONTAINS strä",Strängnäs?,"BOOL_OP,OR,COMPOSITE_TEST,""""""1"""""",TEST_CLAUSE,TEST @Value(master_site_name) = Väg 225 obj 15 och 18",Södertälje?,"BOOL_OP,OR,COMPOSITE_TEST,""""""1"""""",TEST_CLAUSE,TEST @Value(master_site_name) = Kv Tulpanen Norrköping FU",Norrköping?,"BOOL_OP,OR,COMPOSITE_TEST,""""""1"""""",TEST_CLAUSE,TEST @Value(master_site_name) = Verkstadsvägen SU 2009",Motala?,"BOOL_OP,OR,COMPOSITE_TEST,""""""1"""""",TEST_CLAUSE,TEST @Value(master_site_name) = Kärrvallen",Lund?,"BOOL_OP,OR,COMPOSITE_TEST,""""""1"""""",TEST_CLAUSE,CASE_INSENSITIVE_TEST @Value(project_info_Uppdragsgivare) CONTAINS Helsingborgs",Helsingborg?,"BOOL_OP,OR,COMPOSITE_TEST,""""""1"""""",TEST_CLAUSE,TEST @Value(master_site_name) = Kv. Påfågeln 13",Ängelholm,"BOOL_OP,OR,COMPOSITE_TEST,""""""1"""""",TEST_CLAUSE,TEST @Value(master_site_name) = E4:35 SU",Örkelljunga?,"BOOL_OP,OR,COMPOSITE_TEST,""""""1 OR 2"""""",TEST_CLAUSE,TEST @Value(master_site_archive) = s2007040
      TEST @Value(master_site_archive) = s2008030",Poltava,"BOOL_OP,OR,COMPOSITE_TEST,""""""1"""""",TEST_CLAUSE,TEST @Value(master_site_archive) = testremote",skräp?,"BOOL_OP,OR,COMPOSITE_TEST,""""""1 OR 2"""""",TEST_CLAUSE,TEST @Value(master_site_name) = Anfasteröd
      TEST @Value(master_site_name) = Anfasteröd 1:114",Anfasteröd-se ant angåend koordsys
    Västerås? -> GtransReprojector_7
    Malmö? -> GtransReprojector_3
    Aranäs-gbg? -> GtransReprojector_2
    Örebro? -> GtransReprojector_4
    Arbåga -> GtransReprojector_8
    Strängnäs? -> GtransReprojector_9
    Södertälje? -> GtransReprojector_6
    Norrköping? -> GtransReprojector_10
    Motala? -> GtransReprojector_5
    Lund? -> GtransReprojector
    Helsingborg? -> Reprojector_2
    Örkelljunga? -> GtransReprojector_11
Note: ej 3020, 3008
Reprojector_2
    DEST = EPSG:3006
    INTERPOLATION_TYPE_NAME = Nearest Neighbor
    RASTER_CELL_SIZE = Preserve Cells
    RASTER_TOLERANCE = 0.0
    SOURCE = EPSG:3008
GeometryRemover
    -> FeatureMerger_5 [SUPPLIER]
FeatureMerger_5
    ATTR_ACCUM_MODE = Merge Supplier
    ATTR_CONFLICT_RES = Use Requestor
    IGNORE_NULLS = No
    JOIN_KEYS = @Value(intrasisarchive) @Value(intrasisarchive) AUTO
    MERGE_TYPE = Attributes Only
    PROCESS_DUPS = NO
    REJECT_NULL_MISSING_KEYS = No
    SUPPLIERS_FIRST = No
    MERGED -> archives_check_geom (writer OGCGEOPACKAGE_5)
Note: Lokala system att be om från LM / Helsingborg / Vasterås / Arbåga / Strängnäs / Södertälje / Nyköping / Norrköping / Motala / Örkelljunga
archives_check_geom (writer OGCGEOPACKAGE_5)
    attributes: intrasisarchive text(200), pk mediumint, SiteId text, Plats text, Lst Dnr text, Raä Dnr text, Inventarienummer text, Projektkod text, Projektnamn text, Projektledare text, Uppdragsgivare text, Exploateringstyp text, Undersökningstyp text, Slutdatum text, Beskrivning text, fid int, id int, lage text(200), numOfFeature int, geom_intrasisarchive text(200), agg_feat int, UUID_kix text(200), master_site_name text(54), master_site_archive text(17), master_uppdrag_nr int, master_kmr_uppdragsnummer int, master_UUID text(37), master_kmr_id text(37), master_Uppdaterat UUID text(37), master_Kommentar text(685),
      master_H text(4), master_col9 text(74), master__length_uppdrag_nr text(20), link_fornsok text(200), master_uppdrag_ny text(200), _relationships{}.undersokningsomraden_id text(255), _relationships{}.de9im text, _relationships{}.pass{} text, _related_suppliers int, ok_kix text(200), project_info_intrasisarchive text(200), project_info_pk mediumint, project_info_SiteId text, project_info_Plats text, project_info_Lst Dnr text, project_info_Raä Dnr text, project_info_Inventarienummer text, project_info_Projektkod text, project_info_Projektnamn text, project_info_Projektledare text, project_info_Uppdragsgivare text, project_info_Exploateringstyp text, project_info_Undersökningstyp text, project_info_Slutdatum text, project_info_Beskrivning text, project_info_fid int, project_info_id int
ListConcatenator
    DROP_EMPTY_PARTS = No
    LIST_ATTR = _relationships{}.undersokningsomraden_id
    SEP = " , "
    VAL_ATTR = _traff_med_uo_id
    -> FeatureMerger [SUPPLIER]
FeatureMerger
    ATTR_ACCUM_MODE = Merge Supplier
    ATTR_CONFLICT_RES = Use Requestor
    IGNORE_NULLS = No
    JOIN_KEYS = @Value(intrasisarchive) @Value(master_site_archive) AUTO
    MERGE_TYPE = Attributes Only
    PROCESS_DUPS = NO
    REJECT_NULL_MISSING_KEYS = No
    SUPPLIERS_FIRST = No
    MERGED -> archives_check_uuid (writer OGCGEOPACKAGE_5)
archives_check_uuid (writer OGCGEOPACKAGE_5)
    attributes: intrasisarchive text(200), pk mediumint, SiteId text, Plats text, Lst Dnr text, Raä Dnr text, Inventarienummer text, Projektkod text, Projektnamn text, Projektledare text, Uppdragsgivare text, Exploateringstyp text, Undersökningstyp text, Slutdatum text, Beskrivning text, fid int, id int,PrimaryKey, geom_intrasisarchive text(200), agg_feat int, UUID_kix text(200), master_site_name text(54), master_site_archive text(17), master_uppdrag_nr int, master_kmr_uppdragsnummer int, master_UUID text(37), master_kmr_id text(37), master_Uppdaterat UUID text(37), master_Kommentar text(685), master_H text(4), master_col9 text(74),
      master__length_uppdrag_nr text(20), link_fornsok text(200), master_uppdrag_ny text(200), _relationships{}.undersokningsomraden_id text(255), _relationships{}.de9im text, _relationships{}.pass{} text, _related_suppliers int, ok_kix text(200), project_info_intrasisarchive text(200), project_info_pk mediumint, project_info_SiteId text, project_info_Plats text, project_info_Lst Dnr text, project_info_Raä Dnr text, project_info_Inventarienummer text, project_info_Projektkod text, project_info_Projektnamn text, project_info_Projektledare text, project_info_Uppdragsgivare text, project_info_Exploateringstyp text, project_info_Undersökningstyp text, project_info_Slutdatum text, project_info_Beskrivning text, project_info_fid int, project_info_id int, _traff_med_uo_id text

Bookmark: gravda ytor
arkeologiska_uppdrag_grävda_ytor_sverige_linestring (reader OGCGEOPACKAGE_2)
    attributes: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
arkeologiska_uppdrag_grävda_ytor_sverige_point (reader OGCGEOPACKAGE_2)
    attributes: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
arkeologiska_uppdrag_grävda_ytor_sverige_polygon (reader OGCGEOPACKAGE_2)
    attributes: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

Bookmark: uom
arkeologiska_uppdrag_undersökningsområden_sverige_linestring (reader OGCGEOPACKAGE_3)
    attributes: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
arkeologiska_uppdrag_undersökningsområden_sverige_point (reader OGCGEOPACKAGE_3)
    attributes: id text(255), uppdragsnummer text(9), beslutande_myndighet text(255), beslutsdatum date, diarienummer text(255), uppdragstyp text(255), utforande_organisation text(255), nollresultat text(9), url text(255), status text(255), lan text, kommun text, socken text, fid int,PrimaryKey
    -> Aggregator
arkeologiska_uppdrag_undersökningsområden_sverige_polygon (reader OGCGEOPACKAGE_3)
    attributes: id text(255), uppdragsnummer text(9), beslutande_myndighet text(255), beslutsdatum date, diarienummer text(255), uppdragstyp text(255), utforande_organisation text(255), nollresultat text(9), url text(255), status text(255), lan text, kommun text, socken text, fid int,PrimaryKey
    -> Aggregator
Aggregator
    ACCUM_ATTRS_NAME = Use Attributes From One Feature
    AGGREGATE_TYPE = Homogeneous Collection (If Possible)
    GROUP_BY = id
    MODE = Geometry - Assemble One Level
    SEP = ,
    AGGREGATE -> Bufferer_2
Bufferer_2
    ANGLE = 22.5
    CAP_STYLE = Arc
    CORNER_STYLE = Arc
    MODE = AREA
    OFFSET = 200
    OFFSET_UNITS = METERS
    PRECISION = APPROX
    BUFFERED -> BulkAttributeRenamer_3
BulkAttributeRenamer_3
    ATTRCHOICE = All Attributes
    MODE_CHOICE = RENAME
    PATTERN_ACTION_DISP = ADDPREFIX
    REPLACE_STR = undersokningsomraden_
    -> SpatialRelator [Supplier]

Bookmark: New Bookmark
badeInneOchUte (reader OGCGEOPACKAGE_1)
    attributes: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
externa (reader OGCGEOPACKAGE_1)
    attributes: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
inom (reader OGCGEOPACKAGE_1)
    attributes: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
utanforKollaUpp (reader OGCGEOPACKAGE_1)
    attributes: intrasisarchive text(200), lage text(200), numOfFeature int, pk mediumint, SiteId text, Plats text, Lst Dnr text, Raä Dnr text, Inventarienummer text, Projektkod text, Projektnamn text, Projektledare text, Uppdragsgivare text, Exploateringstyp text, Undersökningstyp text, Slutdatum text, Beskrivning text, fid int, id int,PrimaryKey
    -> FeatureMerger_3 [SUPPLIER]

Bookmark: Lund--fixad i urdar db
GtransReprojector_3
    INTERPOLATION_TYPE_NAME = Nearest Neighbor
    RASTER_CELL_SIZE = Square Cells
    RASTER_TOLERANCE = 0.0
    TRANSLATION_FILE = $(FME_HOME)Reproject\Gtrans\Sys\Lund_lokalt-SWEREF991330.TF
    REPROJECTED -> Reprojector_4
Reprojector_4
    DEST = EPSG:3006
    INTERPOLATION_TYPE_NAME = Nearest Neighbor
    RASTER_CELL_SIZE = Preserve Cells
    RASTER_TOLERANCE = 0.0
    SOURCE = EPSG:3008

Bookmark: Örebro-fixade i urdar
GtransReprojector_4
    INTERPOLATION_TYPE_NAME = Nearest Neighbor
    RASTER_CELL_SIZE = Square Cells
    RASTER_TOLERANCE = 0.0
    TRANSLATION_FILE = $(FME_HOME)Reproject\Gtrans\Sys\Orebro_RTR07-SWEREF99_1500.tf
    REPROJECTED -> Reprojector_5
Reprojector_5
    DEST = EPSG:3006
    INTERPOLATION_TYPE_NAME = Nearest Neighbor
    RASTER_CELL_SIZE = Preserve Cells
    RASTER_TOLERANCE = 0.0
    SOURCE = EPSG:3009

Bookmark: Lund fixat i urdar
GtransReprojector
    INTERPOLATION_TYPE_NAME = Nearest Neighbor
    RASTER_CELL_SIZE = Square Cells
    RASTER_TOLERANCE = 0.0
    TRANSLATION_FILE = $(FME_HOME)Reproject\Gtrans\Sys\Lund_lokalt-SWEREF991330.TF
    REPROJECTED -> Reprojector
Reprojector
    DEST = EPSG:3006
    INTERPOLATION_TYPE_NAME = Nearest Neighbor
    RASTER_CELL_SIZE = Preserve Cells
    RASTER_TOLERANCE = 0.0
    SOURCE = EPSG:3008

Bookmark: Västerås fixad i urdar även srid
GtransReprojector_7
    INTERPOLATION_TYPE_NAME = Nearest Neighbor
    RASTER_CELL_SIZE = Square Cells
    RASTER_TOLERANCE = 0.0
    TRANSLATION_FILE = $(FME_HOME)Reproject\Gtrans\Sys\VS47_SWEREF991630.tf
    REPROJECTED -> Reprojector_7
Reprojector_7
    DEST = EPSG:3006
    INTERPOLATION_TYPE_NAME = Nearest Neighbor
    RASTER_CELL_SIZE = Preserve Cells
    RASTER_TOLERANCE = 0.0
    SOURCE = EPSG:3010

Bookmark: södertälje-fixat!! i urdar + SRID
GtransReprojector_6
    INTERPOLATION_TYPE_NAME = Nearest Neighbor
    RASTER_CELL_SIZE = Square Cells
    RASTER_TOLERANCE = 0.0
    TRANSLATION_FILE = $(FME_HOME)Reproject\Gtrans\Sys\stj_lok_sweref991800.tf
    REPROJECTED -> Reprojector_9
Reprojector_9
    DEST = EPSG:3006
    INTERPOLATION_TYPE_NAME = Nearest Neighbor
    RASTER_CELL_SIZE = Preserve Cells
    RASTER_TOLERANCE = 0.0
    SOURCE = EPSG:3011

Bookmark: örkelljunga fixat i urdAR + SRID
GtransReprojector_11
    INTERPOLATION_TYPE_NAME = Nearest Neighbor
    RASTER_CELL_SIZE = Square Cells
    RASTER_TOLERANCE = 0.0
    TRANSLATION_FILE = $(FME_HOME)Reproject\Gtrans\Sys\Orkelljunga.tf
    REPROJECTED -> Reprojector_12
Reprojector_12
    DEST = EPSG:3006
    INTERPOLATION_TYPE_NAME = Nearest Neighbor
    RASTER_CELL_SIZE = Preserve Cells
    RASTER_TOLERANCE = 0.0
    SOURCE = EPSG:3008

Bookmark: hitter ej
GtransReprojector_8
    INTERPOLATION_TYPE_NAME = Nearest Neighbor
    RASTER_CELL_SIZE = Square Cells
    RASTER_TOLERANCE = 0.0
    TRANSLATION_FILE = $(FME_HOME)Reproject\Gtrans\Sys\arboga_hastnas_sweref991630.tf
    REPROJECTED -> Reprojector_6
Note: ej 3021 som det står i projektet
Reprojector_6
    DEST = EPSG:3006
    INTERPOLATION_TYPE_NAME = Nearest Neighbor
    RASTER_CELL_SIZE = Preserve Cells
    RASTER_TOLERANCE = 0.0
    SOURCE = EPSG:3010

Bookmark: ej str-lokala löst koord
GtransReprojector_9
    INTERPOLATION_TYPE_NAME = Nearest Neighbor
    RASTER_CELL_SIZE = Square Cells
    RASTER_TOLERANCE = 0.0
    TRANSLATION_FILE = $(FME_HOME)Reproject\Gtrans\Sys\strangnas_rtr07_sweref991630.tf
    REPROJECTED -> Reprojector_10
Reprojector_10
    DEST = EPSG:3006
    INTERPOLATION_TYPE_NAME = Nearest Neighbor
    RASTER_CELL_SIZE = Preserve Cells
    RASTER_TOLERANCE = 0.0
    SOURCE = EPSG:3010

Bookmark: ej norrköping lokalt
GtransReprojector_10
    INTERPOLATION_TYPE_NAME = Nearest Neighbor
    RASTER_CELL_SIZE = Square Cells
    RASTER_TOLERANCE = 0.0
    TRANSLATION_FILE = $(FME_HOME)Reproject\Gtrans\Sys\Norrkoping_RT90-SWEREF991630.tf
    REPROJECTED -> Reprojector_11
Reprojector_11
    DEST = EPSG:3006
    INTERPOLATION_TYPE_NAME = Nearest Neighbor
    RASTER_CELL_SIZE = Preserve Cells
    RASTER_TOLERANCE = 0.0
    SOURCE = EPSG:3010

Bookmark: motala minus
GtransReprojector_5
    INTERPOLATION_TYPE_NAME = Nearest Neighbor
    RASTER_CELL_SIZE = Square Cells
    RASTER_TOLERANCE = 0.0
    TRANSLATION_FILE = $(FME_HOME)Reproject\Gtrans\Sys\Motala_lokalt-SWEREF991500.tf
    REPROJECTED -> Reprojector_8
Reprojector_8
    DEST = EPSG:3006
    INTERPOLATION_TYPE_NAME = Nearest Neighbor
    RASTER_CELL_SIZE = Preserve Cells
    RASTER_TOLERANCE = 0.0
    SOURCE = EPSG:3009

Bookmark: hittar ej-ej lokalt
Note: ej arbåga
GtransReprojector_2
    INTERPOLATION_TYPE_NAME = Nearest Neighbor
    RASTER_CELL_SIZE = Square Cells
    RASTER_TOLERANCE = 0.0
    TRANSLATION_FILE = $(FME_HOME)Reproject\Gtrans\Sys\arboga_rtr07_sweref991630.tf
    REPROJECTED -> Reprojector_3
Reprojector_3
    DEST = EPSG:3006
    INTERPOLATION_TYPE_NAME = Nearest Neighbor
    RASTER_CELL_SIZE = Preserve Cells
    RASTER_TOLERANCE = 0.0
    SOURCE = EPSG:3010
