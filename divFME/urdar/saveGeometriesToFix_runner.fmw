FME workspace saveGeometriesToFix_runner.fmw

Parameters:
- SourceDataset_OGCGEOPACKAGE = C:\Users\krima354\Work Folders\Documents\kicki_arbetsfiler\urdar_arbetsfiler\intrasis_archive_checkGeom.gpkg   # GeoPackage File
- folder_param = C:\Users\krima354\Work Folders\Documents\kicki_arbetsfiler\urdar_arbetsfiler\utanfor3006_ses_over\20231004   # Select a Folder
- host_choice = urdar   # host

Readers:
- OGCGEOPACKAGE_1: OGCGEOPACKAGE from $(SourceDataset_OGCGEOPACKAGE) in EPSG:3006

archives_check_geom (reader OGCGEOPACKAGE_1)
    attributes: intrasisarchive text(200), pk mediumint, SiteId text, Plats text, Lst Dnr text, Raä Dnr text, Inventarienummer text, Projektkod text, Projektnamn text, Projektledare text, Uppdragsgivare text, Exploateringstyp text, Undersökningstyp text, Slutdatum text, Beskrivning text, fid int, id int, lage text(200), numOfFeature int, geom_intrasisarchive text(200), agg_feat int, UUID_kix text(200), master_site_name text(54), master_site_archive text(17), master_uppdrag_nr int, master_kmr_uppdragsnummer int, master_UUID text(37), master_kmr_id text(37), master_Uppdaterat UUID text(37), master_Kommentar text(685),
      master_H text(4), master_col9 text(74), master__length_uppdrag_nr text(20), link_fornsok text(200), master_uppdrag_ny text(200), _relationships.undersokningsomraden_id text, _relationships.de9im text, _relationships.pass{} text, _related_suppliers int, ok_kix text(200), project_info_intrasisarchive text(200), project_info_pk mediumint, project_info_SiteId text, project_info_Plats text, project_info_Lst Dnr text, project_info_Raä Dnr text, project_info_Inventarienummer text, project_info_Projektkod text, project_info_Projektnamn text, project_info_Projektledare text, project_info_Uppdragsgivare text, project_info_Exploateringstyp text, project_info_Undersökningstyp text, project_info_Slutdatum text, project_info_Beskrivning text, project_info_fid int, project_info_id int, id_0 int,PrimaryKey
    -> AttributeManager
AttributeManager
    ATTR_TABLE = SET_TO gpkg_fix_file = $(folder_param)\@Value(intrasisarchive)_fix.gpkg
    -> WorkspaceRunner
WorkspaceRunner
    BLOCKING = Yes
    WORKSPACE_FILE = $(FME_MF_DIR)saveGeometriesToFix.fmw
    WORKSPACE_PARAMETERS = SourceDataset_POSTGIS_2,@Value(intrasisarchive),host_choice,$(host_choice),DestDataset_OGCGEOPACKAGE,@Value(gpkg_fix_file)
