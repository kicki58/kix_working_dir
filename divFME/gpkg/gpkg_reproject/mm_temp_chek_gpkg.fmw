FME workspace mm_temp_chek_gpkg.fmw

Parameters:
- SourceDataset_XLSXR = Z:\3 - AGES\MalmöM\Leverans 1\2 - Bearbetning\databaser_malmo20240531.xlsx   # Source Microsoft Excel File(s)
- SourceDataset_PATH = C:\ny_slask\mm_3\3 - Klar\3 - Klar   # INCLUDE_WEB_BROWSER Source Folder and File Pathnames Folder

Readers:
- XLSXR_1: XLSXR from $(SourceDataset_XLSXR)
- PATH_1: PATH from $(SourceDataset_PATH)

Geopackages (reader XLSXR_1)
    attributes: database char(29), converted char(26), reprojectet char(26), Inom_Skåne char(58), Coordinate System char(68), Rapport char(2), Comments char(81)
    -> AttributeFilter
    -> FeatureMerger [REQUESTOR]
AttributeFilter
    ATTR_NAME = reprojectet
    ATTR_VALUES = <Empty>,<Missing>,<Null>,<Unfiltered>,File is not exist,FME_NULL_VALUE,inga geometrier,intrasis filer saknas,ja,ligger i Enköping!!,nej,testa manuell rektifiering
PATH (reader PATH_1)
    attributes: path_unix buffer, path_windows buffer, path_rootname buffer, path_filename buffer, path_extension buffer, path_directory_unix buffer, path_directory_windows buffer, path_type char(10)
    -> FeatureMerger [SUPPLIER]
FeatureMerger
    ATTR_ACCUM_MODE = Merge Supplier
    ATTR_CONFLICT_RES_LOOKUP = REQUESTOR_IF_CONFLICT
    IGNORE_NULLS = No
    JOIN_KEYS = @LowerCase(@Value(database)) @LowerCase(@Value(path_rootname)) AUTO
    MERGE_TYPE = Attributes Only
    PROCESS_DUPS = NO
    REJECT_NULL_MISSING_KEYS = No
    SUPPLIERS_FIRST = No
    ATTR_CONFLICT_RES = Use Requestor
    UNMERGED_REQUESTOR -> Tester
Tester
    BOOL_OP = OR
    TEST_CLAUSE = TEST @Value(reprojectet) = inga geometrier
    TEST_MODE = TEST
