FME workspace 1_make_features_features.fmw

Parameters:
- SourceDestDataset_SQLITE3 = C:\ny_slask\kulturparken_smaland\gpkg\unknown\x_1500k\reprojected\sm20034.gpkg   # SQLite Database

Readers:
- SQLITE3_1: SQLITE3 from $(SourceDestDataset_SQLITE3)

Writers:
- SQLITE3_2: SQLITE3 to $(SourceDestDataset_SQLITE3)

gpkg_contents (reader SQLITE3_1)
    attributes: table_name text,Unique, data_type text, identifier text,Unique, description text, last_change text, min_x double, min_y double, max_x double, max_y double, srs_id integer
    -> StatisticsCalculator_2
StatisticsCalculator_2
    ATTR_ACCUM_MODE = None
    CALCULATION_MODE = PER_ATTR
    FEAT_STATS = max_x,NUMERIC_MODE,,MAX,,,,,,,,,,,;min_x,NUMERIC_MODE,MIN,,,,,,,,,,,,;max_y,NUMERIC_MODE,,MAX,,,,,,,,,,,;min_y,NUMERIC_MODE,MIN,,,,,,,,,,,,;srs_id,NUMERIC_MODE,,,,,MEAN,,,,,,,,;last_change,LEXICAL,MIN,,,<Unused>,<Unused>,,,,<Unused>,<Unused>,<Unused>,,
    GROUP_BY = data_type
    SUMMARY -> AttributeManager_2
AttributeManager_2
    ATTR_TABLE:
      RENAME_SET_VALUE max_x.max > max_x
      RENAME_SET_VALUE min_x.min > min_x
      RENAME_SET_VALUE max_y.max > max_y
      RENAME_SET_VALUE min_y.min > min_y
      RENAME_SET_VALUE srs_id.mean > srs_id
      RENAME_SET_VALUE last_change.min > last_change
      SET_TO table_name = features
      SET_TO identifier = features
      SET_TO description
    -> gpkg_contents (writer SQLITE3_2)
gpkg_contents (writer SQLITE3_2)
    attributes: table_name text,Unique, data_type text, identifier text,Unique, description text, last_change text, min_x double, min_y double, max_x double, max_y double, srs_id integer
gpkg_geometry_columns (reader SQLITE3_1)
    attributes: table_name text,Unique, column_name text,Unique, geometry_type_name text, srs_id integer, z integer, m integer
    -> StatisticsCalculator
StatisticsCalculator
    ATTR_ACCUM_MODE = None
    CALCULATION_MODE = NUMERIC
    FEAT_STATS = srs_id,NUMERIC_MODE,,,,,MEAN,,,,,,,,;m,NUMERIC_MODE,,,,,MEAN,,,,,,,,;z,NUMERIC_MODE,,,,,MEAN,,,,,,,,
    GROUP_BY = column_name
    SUMMARY -> AttributeManager
AttributeManager
    ATTR_TABLE:
      SET_TO column_name = geom
      RENAME_SET_VALUE srs_id.mean > srs_id
      RENAME_SET_VALUE m.mean > m
      RENAME_SET_VALUE z.mean > z
      SET_TO table_name = features
      SET_TO geometry_type_name = GEOMETRY
    -> gpkg_geometry_columns (writer SQLITE3_2)
gpkg_geometry_columns (writer SQLITE3_2)
    attributes: table_name text,Unique, column_name text,Unique, geometry_type_name text, srs_id integer, z integer, m integer
