FME workspace 2_reproject.fmw

Parameters:
- reprojectDestDataset_OGCGEOPACKAGE_2 = C:\ny_slask\jonkoping\gpkg_export2\not_comverted\temp\JM2004174.gpkg   # Dest GeoPackage File reproject
- SOURCE_srs = EPSG:3008   # EnableReadFromFeature:Yes Source Coordinate System
- TRANSLATION_FILE = $(FME_HOME)Reproject\Gtrans\Sys\varnamo_lokalt_sweref991330.tf   # Translation File
- SourceDataset_OGCGEOPACKAGE_3 = C:\ny_slask\jonkoping\gpkg_export2\not_comverted\JM2004174.gpkg   # GeoPackage File
- SourceDataset_OGCGEOPACKAGE = C:\ny_slask\jonkoping\gpkg_export2\not_comverted\JM2004174.gpkg   # GeoPackage at omprojecera

Readers:
- OGCGEOPACKAGE_2: OGCGEOPACKAGE from $(SourceDataset_OGCGEOPACKAGE)
- OGCGEOPACKAGE_5: OGCGEOPACKAGE from $(SourceDataset_OGCGEOPACKAGE_3)

Writers:
- OGCGEOPACKAGE_3: OGCGEOPACKAGE to $(reprojectDestDataset_OGCGEOPACKAGE_2)

project_information (reader OGCGEOPACKAGE_5)
    attributes: attribute_label text(15), Plats text(24), Projektledare text(17), Undersöknings Id text(10), Undersökningstyp text(17), Uppdragsgivare text(15), Raä Dnr text(6), id int,PrimaryKey, Class text, Color int, GeoObjectId mediumint, IntrasisId int, Name text, SubClass text, SymbolId mediumint, attribute_id int, attribute_unit text, attribute_value text, attributes text, base_id int, base_text text, class int, data_type text, fid int, geom text, geometry_count int, object_id mediumint, related_id int, related_text text, spatial_type text
    -> AttributeFilter
AttributeFilter
    ATTR_NAME = fme_feature_type
    ATTR_VALUES = <Empty>,<Missing>,<Null>,<Unfiltered>,project_information
    PRESERVE_FEATURE_ORDER_LOOKUP = PER_OUTPUT_PORT
    project_information -> SchemaScanner
SchemaScanner
    CASE = No
    EMPTY_ATTR_HANDLING = IGNORE
    HOLD = Yes
    IGNORE_REGEXP = ^fme_<pipe>^multi_
    INCLUDE_FORMAT_ATTR = No
    NUMERIC_ALLOW_LEADING_ZEROES = Yes
    SCHEMA_NAME_ATTR = fme_feature_type_name
    UNBOUNDED_NUMBERS = Yes
    UNBOUNDED_STRINGS = No
    -> GtransReprojector_2
    <SCHEMA> -> project_information (writer OGCGEOPACKAGE_3)
GtransReprojector_2
    INTERPOLATION_TYPE = ,NearestNeighbor
    RASTER_CELL_SIZE_LOOKUP = ,SquareCells
    RASTER_TOLERANCE = 0.0
    TRANSLATION_FILE = $(TRANSLATION_FILE)
    INTERPOLATION_TYPE_NAME = Nearest Neighbor
    RASTER_CELL_SIZE = Square Cells
    REPROJECTED -> Reprojector_2
Reprojector_2
    DEST = EPSG:3006
    INTERPOLATION_TYPE = ,NearestNeighbor
    RASTER_CELL_SIZE_LOOKUP = ,PreserveCells
    RASTER_TOLERANCE = 0.0
    SOURCE = $(SOURCE_srs)
    INTERPOLATION_TYPE_NAME = Nearest Neighbor
    RASTER_CELL_SIZE = Preserve Cells
    REPROJECTED -> project_information (writer OGCGEOPACKAGE_3)
project_information (writer OGCGEOPACKAGE_3)
    attributes: pk mediumint, SiteId text, Plats text, Lst Dnr text, Raä Dnr text, Inventarienummer text, Projektkod text, Projektnamn text, Projektledare text, Uppdragsgivare text, Exploateringstyp text, Undersökningstyp text, Slutdatum text, Beskrivning text, fid int
features (reader OGCGEOPACKAGE_2)
    attributes: geom text, object_id mediumint, SymbolId mediumint, GeoObjectId mediumint, spatial_type text, fid int,PrimaryKey
    -> GtransReprojector
GtransReprojector
    INTERPOLATION_TYPE = ,NearestNeighbor
    RASTER_CELL_SIZE_LOOKUP = ,SquareCells
    RASTER_TOLERANCE = 0.0
    TRANSLATION_FILE = $(TRANSLATION_FILE)
    INTERPOLATION_TYPE_NAME = Nearest Neighbor
    RASTER_CELL_SIZE = Square Cells
    REPROJECTED -> Reprojector_3
Reprojector_3
    DEST = EPSG:3006
    INTERPOLATION_TYPE = ,NearestNeighbor
    RASTER_CELL_SIZE_LOOKUP = ,PreserveCells
    RASTER_TOLERANCE = 0.0
    SOURCE = $(SOURCE_srs)
    INTERPOLATION_TYPE_NAME = Nearest Neighbor
    RASTER_CELL_SIZE = Preserve Cells
    REPROJECTED -> features (writer OGCGEOPACKAGE_3)
features (writer OGCGEOPACKAGE_3)
    attributes: object_id mediumint, SymbolId mediumint, GeoObjectId mediumint, spatial_type text, fid int,PrimaryKey
