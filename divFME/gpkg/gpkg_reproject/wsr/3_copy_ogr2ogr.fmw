FME workspace 3_copy_ogr2ogr.fmw

Parameters:
- kopia_DestDataset_OGCGEOPACKAGE_3 = C:\ny_slask\jonkoping\gpkg_export2\not_comverted\reprojected\JM2004174.gpkg   # Destination GeoPackage File
- reprojectSourceDataset_OGCGEOPACKAGE_2 = C:\ny_slask\jonkoping\gpkg_export2\not_comverted\temp\JM2004174.gpkg   # Reproject Source GeoPackage File
- qgis_bin = C:\Program Files\QGIS 3.34.2\bin   # path QGIS bin

Creator
    GEOMTYPE = Geometry Object
    NUM = 1
    CREATED -> SystemCaller
    CREATED -> SystemCaller_2
SystemCaller_2 [off]
    CMD = ""C:\Program Files\QGIS 3.34.2\bin\ogr2ogr" -overwrite $(kopia_DestDataset_OGCGEOPACKAGE_3) $(reprojectSourceDataset_OGCGEOPACKAGE_2) features"
SystemCaller
    CMD = ""$(qgis_bin)\ogr2ogr" -overwrite $(kopia_DestDataset_OGCGEOPACKAGE_3) $(reprojectSourceDataset_OGCGEOPACKAGE_2) features project_information"
