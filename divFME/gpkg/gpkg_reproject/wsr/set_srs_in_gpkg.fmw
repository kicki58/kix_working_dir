FME workspace set_srs_in_gpkg.fmw

Parameters:
- reproject = \\argos.storage.uu.se\MyFolder$\krima354\kicki_arbetsfiler\kulturparken_smaland\unknown\working\s2006029.gpkg   # Reprojected gpkg
- srs_to_set = 3006   # SRID to set

Readers:
- SQLITE3_1: SQLITE3 from $(reproject)

Writers:
- SQLITE3_2: SQLITE3 to $(reproject)

Bookmark: contents and columns
gpkg_contents (reader SQLITE3_1)
    attributes: table_name text,Unique, data_type text, identifier text,Unique, description text, last_change text, min_x double, min_y double, max_x double, max_y double, srs_id integer
    -> AttributeManager_3
AttributeManager_3
    ATTR_TABLE:
      SET_TO srs_id = $(srs_to_set)
      SET_TO fme_db_operation = UPDATE
    -> gpkg_contents (writer SQLITE3_2)
gpkg_contents (writer SQLITE3_2)
    attributes: table_name text,Unique, data_type text, identifier text,Unique, description text, last_change text, min_x double, min_y double, max_x double, max_y double, srs_id integer
gpkg_geometry_columns (reader SQLITE3_1)
    attributes: table_name text,Unique, column_name text,Unique, geometry_type_name text, srs_id integer, z integer, m integer
    -> AttributeManager_2
AttributeManager_2
    ATTR_TABLE:
      SET_TO srs_id = $(srs_to_set)
      SET_TO fme_db_operation = UPDATE
    -> gpkg_geometry_columns (writer SQLITE3_2)
gpkg_geometry_columns (writer SQLITE3_2)
    attributes: table_name text,Unique, column_name text,Unique, geometry_type_name text, srs_id integer, z integer, m integer
