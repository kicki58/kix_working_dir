FME workspace set_srs2gpkg.fmw

Parameters:
- SourceDataset_PATH = C:\ny_slask\mm_intrasis2ages\reprojected2sweref99tm\reprojected2sweref99tm   # INCLUDE_WEB_BROWSER Source Folder and File Pathnames Folder
- RECURSE_DIRECTORIES_PATH = NO   # Recurse Into Subfolders
- SourceDataset_XLSXR = C:\ny_slask\mm_intrasis2ages\reprojected2sweref99tm\reprojected2sweref99tm\srid.xlsx   # Source Microsoft Excel File(s)

Readers:
- PATH_1: PATH from $(SourceDataset_PATH)
- XLSXR_1: XLSXR from $(SourceDataset_XLSXR)

alla (reader XLSXR_1)
    attributes: gpkg char(14), srs_id number(4,0), z number(1,0), m number(1,0)
    -> DuplicateFilter
DuplicateFilter
    INPUT_ORDERED_CHOICE_LOOKUP = NO
    KEYATTR = gpkg
    INPUT_ORDERED_CHOICE = No
    UNIQUE -> Tester_2
Tester_2
    BOOL_OP = OR
    TEST_CLAUSE = TEST @Value(srs_id) != 3006
    TEST_MODE = TEST
    PASSED -> FeatureMerger [REQUESTOR]
PATH (reader PATH_1)
    attributes: path_unix buffer, path_windows buffer, path_rootname buffer, path_filename buffer, path_extension buffer, path_directory_unix buffer, path_directory_windows buffer, path_type char(10)
    -> FeatureMerger [SUPPLIER]
FeatureMerger
    ATTR_ACCUM_MODE = Merge Supplier
    ATTR_CONFLICT_RES_LOOKUP = REQUESTOR_IF_CONFLICT
    IGNORE_NULLS = No
    JOIN_KEYS = @Value(gpkg) @Value(path_rootname) AUTO
    MERGE_TYPE_VAL = ATTRIBUTES
    PROCESS_DUPS = NO
    REJECT_NULL_MISSING_KEYS = No
    SUPPLIERS_FIRST = No
    ATTR_CONFLICT_RES = Use Requestor
    MERGE_TYPE = Merge Attributes
    MERGED -> SQLExecutor [INITIATOR]
SQLExecutor
    ATTR_IGNORE_NULLS = No
    COMBINE_ATTRS_OPTIONS = PREFER_RESULT
    COMBINE_GEOM_OPTIONS = RESULT_ONLY
    DATASET = @Value(path_windows)
    FORMAT = OGCGEOPACKAGE
    INPUT_PORT_INITIATOR_CONNECTED = CONNECTED
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = NO
    OGCGEOPACKAGE_READ_BOOLEANS_AS_YES_NO = YES
    OGCGEOPACKAGE_READ_NULLS = YES
    OUTPUT_FEATURES = DATA_ONLY
    SQL_STATEMENT:
      FME_SQL_DELIMITER ;
      select srs_id
      from gpkg_spatial_ref_sys
      where srs_id=3006;
    COMBINE_ATTRS = Keep Result Attributes if Conflict
    COMBINE_GEOM = Result Geometry Only
    RESULT -> Tester
    INITIATOR -> WorkspaceRunner_2
Tester
    BOOL_OP = OR
    TEST_CLAUSE = TEST @Value(srs_id) = 3006
    TEST_MODE = TEST
    PASSED -> WorkspaceRunner
    FAILED -> WorkspaceRunner_2
Note: define coordsys 3006
WorkspaceRunner
    BLOCKING = Yes
    INPUT_PORT_CONNECTED = CONNECTED
    OVERWRITE_LOG_FILE = HONOR
    STDERR_HANDLING = COMBINE
    WORKSPACE_FILE = $(FME_MF_DIR_ENCODED)wsr\add_3006_def2gpkg.fmw
    WORKSPACE_PARAMETERS = add3006,@Value(path_windows)
    SUCCEEDED -> WorkspaceRunner_2
Note: fix gpkg-add to geom_collums mm
WorkspaceRunner_2
    BLOCKING = Yes
    INPUT_PORT_CONNECTED = CONNECTED
    OVERWRITE_LOG_FILE = HONOR
    STDERR_HANDLING = COMBINE
    WORKSPACE_FILE = $(FME_MF_DIR_ENCODED)wsr\set_srs_in_gpkg.fmw
    WORKSPACE_PARAMETERS = reproject,@Value(path_windows),srs_to_set,@Value(srs_id)
