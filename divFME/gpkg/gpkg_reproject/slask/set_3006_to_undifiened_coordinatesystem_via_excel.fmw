FME workspace set_3006_to_undifiened_coordinatesystem_via_excel.fmw

Parameters:
- SourceDataset_PATH = C:\ny_slask\mm_3\3 - Klar\3 - Klar   # INCLUDE_WEB_BROWSER Source Folder and File Pathnames Folder
- SourceDataset_XLSXR = C:\ny_slask\mm_3\3 - Klar\3 - Klar\srid.xlsx   # Source Microsoft Excel File(s)
- PATH_IN_RECURSE_DIRECTORIES_PATH_2 = NO   # Recurse Into Subfolders

Readers:
- PATH_1: PATH from $(SourceDataset_PATH)
- XLSXR_1: XLSXR from $(SourceDataset_XLSXR)

0 (reader XLSXR_1)
    attributes: gpkg char(8), srs_id number(1,0), z number(1,0), m number(1,0)
    -> FeatureMerger [REQUESTOR]
PATH (reader PATH_1)
    attributes: path_unix buffer, path_windows buffer, path_rootname buffer, path_filename buffer, path_extension buffer, path_directory_unix buffer, path_directory_windows buffer, path_type char(10)
    -> FeatureMerger [SUPPLIER]
FeatureMerger
    ATTR_ACCUM_MODE = Merge Supplier
    ATTR_CONFLICT_RES_LOOKUP = REQUESTOR_IF_CONFLICT
    IGNORE_NULLS = No
    JOIN_KEYS = @Value(gpkg) @Value(path_rootname) AUTO
    MERGE_TYPE = Attributes Only
    PROCESS_DUPS = NO
    REJECT_NULL_MISSING_KEYS = No
    SUPPLIERS_FIRST = No
    ATTR_CONFLICT_RES = Use Requestor
    MERGED -> WorkspaceRunner
Note: define coordsys 3006
WorkspaceRunner
    BLOCKING = Yes
    WORKSPACE_FILE = $(FME_MF_DIR_ENCODED)wsr\add_3006_def2gpkg.fmw
    WORKSPACE_PARAMETERS = add3006,@Value(path_windows)
    SUCCEEDED -> WorkspaceRunner_2
Note: fix gpkg-add to geom_collums mm
WorkspaceRunner_2
    BLOCKING = Yes
    WORKSPACE_FILE = $(FME_MF_DIR_ENCODED)wsr\set_srs_in_gpkg.fmw
    WORKSPACE_PARAMETERS = reproject,@Value(path_windows),srs_to_set,3006
