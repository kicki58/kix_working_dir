FME workspace clipp_aggregate.fmw

Parameters:
- SourceDataset_OGCGEOPACKAGE = C:\ny_slask\test_agg_all\alla_intrasis\alla_features_objects_test6.gpkg   # GeoPackage File
- DestDataset_OGCGEOPACKAGE = C:\ny_slask\test_agg_all\alla_intrasis\alla_features_objects_inom_sverige2.gpkg   # GeoPackage File
- SourceDataset_POSTGIS = uuc-srv390_ages_5434   # Connection

Readers:
- POSTGIS_1: POSTGIS from $(SourceDataset_POSTGIS)
- OGCGEOPACKAGE_1: OGCGEOPACKAGE from $(SourceDataset_OGCGEOPACKAGE)

Writers:
- OGCGEOPACKAGE_2: OGCGEOPACKAGE to $(DestDataset_OGCGEOPACKAGE)

sverige_buff5000 (reader POSTGIS_1)
    attributes: landskap varchar(254), kommentar varchar(150), skala varchar(100), _area_utan_buffer float8
    -> Clipper [CLIPPER]
project_information (reader OGCGEOPACKAGE_1)
    attributes: siteid text, id int,PrimaryKey
    -> Clipper [CANDIDATE]
features (reader OGCGEOPACKAGE_1)
    attributes: object_id mediumint, symbolid mediumint, geoobjectid mediumint, spatial_type text, swedigarch_id text(200), id int,PrimaryKey
    -> Clipper [CANDIDATE]
Clipper
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> FeatureTypeFilter
FeatureTypeFilter
    ATTRIBUTES = <Blank>,<Unfiltered>,project_information,features
    ATTRIBUTE_INFO = common.sverige_buff5000,landskap,kommentar,skala,_area_utan_buffer,features,object_id,symbolid,geoobjectid,spatial_type,swedigarch_id,id,project_information,siteid,id
    project_information -> project_information (writer OGCGEOPACKAGE_2)
    features -> AttributeRemover
    features -> AttributeManager_4
AttributeRemover
    REMOVE_ATTRS = geoobjectid,id,object_id,spatial_type,symbolid
    -> GeometryRemover
GeometryRemover
    REMOVE_COORDSYS = No
    -> AttributeManager
AttributeManager
    ATTR_TABLE = SET_TO intrasis_db (varchar(200)) = @LowerCase(@Substring(@Value(swedigarch_id),0,@FindString(@Value(swedigarch_id),_,0,caseSensitive=TRUE)))
    -> DuplicateFilter
DuplicateFilter
    INPUT_ORDERED_CHOICE_LOOKUP = NO
    KEYATTR = intrasis_db
    INPUT_ORDERED_CHOICE = No
    UNIQUE -> FeatureMerger [SUPPLIER]
AttributeManager_4
    ATTR_TABLE = SET_TO intrasis_db (varchar(200)) = @LowerCase(@Substring(@Value(swedigarch_id),0,@FindString(@Value(swedigarch_id),_,0,caseSensitive=TRUE)))
    -> features (writer OGCGEOPACKAGE_2)
features (writer OGCGEOPACKAGE_2)
    attributes: swedigarch_id text(200), intrasis_db text(200), object_id mediumint, id int,PrimaryKey, symbolid mediumint, geoobjectid mediumint, spatial_type text
project_information (writer OGCGEOPACKAGE_2)
    attributes: siteid text, id int,PrimaryKey
objects (reader OGCGEOPACKAGE_1)
    attributes: intrasisid int, name text, class text, subclass text, color int, geometry_count int, attributes text, object_id int, swedigarch_id text(200), id int,PrimaryKey
    -> AttributeManager_2
AttributeManager_2
    ATTR_TABLE = SET_TO intrasis_db (varchar(200)) = @LowerCase(@Substring(@Value(swedigarch_id),0,@FindString(@Value(swedigarch_id),_,0,caseSensitive=TRUE)))
    -> FeatureMerger [REQUESTOR]
FeatureMerger
    ATTR_ACCUM_MODE = Merge Supplier
    ATTR_CONFLICT_RES_LOOKUP = REQUESTOR_IF_CONFLICT
    IGNORE_NULLS = No
    JOIN_KEYS = @Value(intrasis_db) @Value(intrasis_db) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> objects (writer OGCGEOPACKAGE_2)
objects (writer OGCGEOPACKAGE_2)
    attributes: swedigarch_id text(200), intrasis_db text(200), intrasisid int, name text, class text, subclass text, color int, geometry_count int, attributes text, object_id int, id int,PrimaryKey
