FME workspace remove_from_aggregate_features_utanfor_sverige.fmw

Parameters:
- SourceDataset_POSTGIS = uuc-srv390_ages_5434   # conn toAGES
- SourceDataset_OGCGEOPACKAGE_3 = C:\ny_slask\gpkg_alla\aggregated.gpkg   # GeoPackage File
- DestDataset_OGCGEOPACKAGE = C:\ny_slask\gpkg_alla\aggregated_inomSverige.gpkg   # GeoPackage File

Readers:
- POSTGIS_1: POSTGIS from $(SourceDataset_POSTGIS)
- OGCGEOPACKAGE_2: OGCGEOPACKAGE from $(SourceDataset_OGCGEOPACKAGE_3)

Writers:
- OGCGEOPACKAGE_1: OGCGEOPACKAGE to $(DestDataset_OGCGEOPACKAGE)

project_information (reader OGCGEOPACKAGE_2)
    attributes: intrasis_name text, pk mediumint, SiteId text, Plats text, Lst Dnr text, Raä Dnr text, Inventarienummer text, Projektkod text, Projektnamn text, Projektledare text, Uppdragsgivare text, Exploateringstyp text, Undersökningstyp text, Slutdatum text, Beskrivning text, id int,PrimaryKey
    -> SpatialFilter [Candidate]
sverige_buff5000 (reader POSTGIS_1)
    attributes: landskap varchar(254), kommentar varchar(150), skala varchar(100), _area_utan_buffer float8
    -> SpatialFilter [Filter]
features (reader OGCGEOPACKAGE_2)
    attributes: intrasis_name text, object_id mediumint, Class text, SubClass text, SymbolId mediumint, GeoObjectId mediumint, spatial_type text, id int,PrimaryKey
    -> SpatialFilter [Candidate]
SpatialFilter
    AGGREGATE_HANDLING = Yes
    BASE_TYPE = Multiple Filters
    CURVE_BOUNDARY_RULE_PARAM = Default Rule
    PASS_CRITERIA = Pass Against One Filter
    PREDATTR = _predicate
    PREDICATES = INTERSECTS CONTAINS
    USE_BOUNDING_BOX = No
    PASSED -> FeatureTypeFilter_2
FeatureTypeFilter_2
    ATTRIBUTES = <Blank>,<Unfiltered>,features,project_information
    ATTRIBUTE_INFO = common.sverige_buff5000,landskap,kommentar,skala,_area_utan_buffer,features,intrasis_name,object_id,Class,SubClass,SymbolId,GeoObjectId,spatial_type,id,project_information,intrasis_name,pk,SiteId,Plats,"Lst Dnr","Raä Dnr",Inventarienummer,Projektkod,Projektnamn,Projektledare,Uppdragsgivare,Exploateringstyp,Undersökningstyp,Slutdatum,Beskrivning,id
    features -> features (writer OGCGEOPACKAGE_1)
    project_information -> project_information (writer OGCGEOPACKAGE_1)
features (writer OGCGEOPACKAGE_1)
    attributes: intrasis_name text, object_id mediumint, Class text, SubClass text, SymbolId mediumint, GeoObjectId mediumint, spatial_type text, id int,PrimaryKey
project_information (writer OGCGEOPACKAGE_1)
    attributes: intrasis_name text, pk mediumint, SiteId text, Plats text, Lst Dnr text, Raä Dnr text, Inventarienummer text, Projektkod text, Projektnamn text, Projektledare text, Uppdragsgivare text, Exploateringstyp text, Undersökningstyp text, Slutdatum text, Beskrivning text, id int,PrimaryKey
objects (reader OGCGEOPACKAGE_2)
    attributes: intrasis_name text, IntrasisId int, Name text, Class text, SubClass text, undertyp text, beskrivning text, tolkning text, tolkningsattribut text, namn text(20), attributes text, geometry_count int, Color int, object_id int, id int,PrimaryKey
    -> objects (writer OGCGEOPACKAGE_1)
objects (writer OGCGEOPACKAGE_1)
    attributes: intrasis_name text, IntrasisId int, Name text, Class text, SubClass text, undertyp text, beskrivning text, tolkning text, tolkningsattribut text, namn text(20), attributes text, geometry_count int, Color int, object_id int, id int,PrimaryKey
