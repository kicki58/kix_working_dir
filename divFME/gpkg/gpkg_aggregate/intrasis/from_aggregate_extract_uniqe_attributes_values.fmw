FME workspace from_aggregate_extract_uniqe_attributes_values.fmw

Parameters:
- SourceDataset_OGCGEOPACKAGE = C:\ny_slask\gpkg_alla\aggregated.gpkg   # GeoPackage File
- DestDataset_OGCGEOPACKAGE = C:\ny_slask\gpkg_alla\alla_attribut9.gpkg   # GeoPackage File

Readers:
- OGCGEOPACKAGE_1: OGCGEOPACKAGE from $(SourceDataset_OGCGEOPACKAGE)

Writers:
- OGCGEOPACKAGE_2: OGCGEOPACKAGE to $(DestDataset_OGCGEOPACKAGE)

project_information (reader OGCGEOPACKAGE_1)
    attributes: intrasis_name text, pk mediumint, SiteId text, Plats text, Lst Dnr text, Raä Dnr text, Inventarienummer text, Projektkod text, Projektnamn text, Projektledare text, Uppdragsgivare text, Exploateringstyp text, Undersökningstyp text, Slutdatum text, Beskrivning text, id int,PrimaryKey
    -> project_information (writer OGCGEOPACKAGE_2)
project_information (writer OGCGEOPACKAGE_2)
    attributes: intrasis_name text, pk mediumint, SiteId text, Plats text, Lst Dnr text, Raä Dnr text, Inventarienummer text, Projektkod text, Projektnamn text, Projektledare text, Uppdragsgivare text, Exploateringstyp text, Undersökningstyp text, Slutdatum text, Beskrivning text, id int,PrimaryKey
objects (reader OGCGEOPACKAGE_1)
    attributes: intrasis_name text, IntrasisId int, Name text, Class text, SubClass text, undertyp text, beskrivning text, tolkning text, tolkningsattribut text, namn text(20), attributes text, geometry_count int, Color int, object_id int, id int,PrimaryKey
    -> Tester_6
    -> Tester_7
    -> Tester_8
    -> Tester_9
    -> Tester_10
    -> objects (writer OGCGEOPACKAGE_2)
    -> Tester_2
objects (writer OGCGEOPACKAGE_2)
    attributes: intrasis_name text, IntrasisId int, Name text, Class text, SubClass text, undertyp text, beskrivning text, tolkning text, tolkningsattribut text, namn text(20), attributes text, geometry_count int, Color int, object_id int, id int,PrimaryKey
Tester_6
    BOOL_OP = OR
    TEST_CLAUSE = TEST Name ATTRIBUTE_HAS_A_VALUE ""
    TEST_MODE = TEST
    PASSED -> ListBuilder
    PASSED -> ListBuilder_15
ListBuilder
    GROUP_BY = Name Class SubClass
    LIST_ATTRS_TO_INCLUDE = Name Class SubClass
    LIST_NAME = _antal
    -> ListElementCounter
ListElementCounter
    CNT_ATTR = antal
    LIST_NAME = _antal{}
    -> FeatureMerger_2 [REQUESTOR]
ListBuilder_15
    GROUP_BY = Class intrasis_name SubClass Name
    LIST_ATTRS_TO_INCLUDE = Class intrasis_name SubClass Name
    LIST_NAME = _list
    -> AttributeRemover_5
AttributeRemover_5
    LIST_ATTRS = _list{} _list{}.Class _list{}.SubClass _list{}.intrasis_name _list{}.Name
    -> ListBuilder_16
ListBuilder_16
    GROUP_BY = Class SubClass Name
    LIST_ATTRS_TO_INCLUDE = intrasis_name
    LIST_NAME = _list
    -> ListElementCounter_11
ListElementCounter_11
    CNT_ATTR = antal_intrasis_projekt
    LIST_NAME = _list{}
    -> FeatureMerger_2 [SUPPLIER]
FeatureMerger_2
    ATTR_ACCUM_MODE = Merge Supplier
    ATTR_CONFLICT_RES_LOOKUP = REQUESTOR_IF_CONFLICT
    CLEANING_TOLERANCE_LOOKUP = AUTO
    CONNECT_Z_MODE_LOOKUP = FIRST_WINS
    GEOM_TYPE_VAL = POLYGONS
    IGNORE_NULLS = No
    JOIN_KEYS = @Value(Class) @Value(Class) AUTO @Value(Name) @Value(Name) AUTO @Value(SubClass) @Value(SubClass) AUTO
    MERGE_COUNT_ATTR = antal_intrasis_projekt
    MERGE_TYPE = Attributes Only
    PROCESS_DUPS = YES
    REJECT_NULL_MISSING_KEYS = No
    SUPPLIERS_FIRST = No
    ATTR_CONFLICT_RES = Use Requestor
    CLEANING_TOLERANCE = Automatic
    CONNECT_Z_MODE = First Wins
    GEOM_TYPE = Build Polygons
    MERGED -> AttributeManager
AttributeManager
    ATTR_TABLE:
      REMOVE _antal{}.Name (buffer)
      REMOVE _antal{}.Class (buffer)
      REMOVE _antal{}.SubClass (buffer)
      REMOVE _list{}.intrasis_name (buffer)
    -> unika_Name (writer OGCGEOPACKAGE_2)
unika_Name (writer OGCGEOPACKAGE_2)
    attributes: Class text, SubClass text, Name text, antal int, antal_intrasis_projekt int
Tester_7
    BOOL_OP = OR
    TEST_CLAUSE = TEST namn ATTRIBUTE_HAS_A_VALUE ""
    TEST_MODE = TEST
    PASSED -> ListBuilder_2
    PASSED -> ListBuilder_17
ListBuilder_2
    GROUP_BY = Class SubClass namn
    LIST_ATTRS_TO_INCLUDE = Class SubClass namn
    LIST_NAME = _antal
    -> ListElementCounter_2
ListElementCounter_2
    CNT_ATTR = antal
    LIST_NAME = _antal{}
    -> FeatureMerger_3 [REQUESTOR]
ListBuilder_17
    GROUP_BY = Class intrasis_name SubClass namn
    LIST_ATTRS_TO_INCLUDE = Class intrasis_name SubClass namn
    LIST_NAME = _list
    -> AttributeRemover_6
AttributeRemover_6
    LIST_ATTRS = _list{} _list{}.Class _list{}.SubClass _list{}.intrasis_name _list{}.namn
    -> ListBuilder_18
ListBuilder_18
    GROUP_BY = Class SubClass namn
    LIST_ATTRS_TO_INCLUDE = intrasis_name
    LIST_NAME = _list
    -> ListElementCounter_12
ListElementCounter_12
    CNT_ATTR = antal_intrasis_projekt
    LIST_NAME = _list{}
    -> FeatureMerger_3 [SUPPLIER]
FeatureMerger_3
    ATTR_ACCUM_MODE = Merge Supplier
    ATTR_CONFLICT_RES_LOOKUP = REQUESTOR_IF_CONFLICT
    CLEANING_TOLERANCE_LOOKUP = AUTO
    CONNECT_Z_MODE_LOOKUP = FIRST_WINS
    GEOM_TYPE_VAL = POLYGONS
    IGNORE_NULLS = No
    JOIN_KEYS = @Value(Class) @Value(Class) AUTO @Value(namn) @Value(namn) AUTO @Value(SubClass) @Value(SubClass) AUTO
    MERGE_COUNT_ATTR = antal_intrasis_projekt
    MERGE_TYPE = Attributes Only
    PROCESS_DUPS = YES
    REJECT_NULL_MISSING_KEYS = No
    SUPPLIERS_FIRST = No
    ATTR_CONFLICT_RES = Use Requestor
    CLEANING_TOLERANCE = Automatic
    CONNECT_Z_MODE = First Wins
    GEOM_TYPE = Build Polygons
    MERGED -> AttributeManager_2
AttributeManager_2
    ATTR_TABLE:
      REMOVE _antal{}.Class (buffer)
      REMOVE _antal{}.SubClass (buffer)
      REMOVE _antal{}.namn (varchar(20))
      REMOVE _list{}.intrasis_name (buffer)
    -> unika_namn (writer OGCGEOPACKAGE_2)
unika_namn (writer OGCGEOPACKAGE_2)
    attributes: Class text, SubClass text, namn text, antal int, antal_intrasis_projekt int
Tester_8
    BOOL_OP = OR
    TEST_CLAUSE = TEST beskrivning ATTRIBUTE_HAS_A_VALUE ""
    TEST_MODE = TEST
    PASSED -> ListBuilder_3
    PASSED -> ListBuilder_13
ListBuilder_3
    GROUP_BY = Class SubClass beskrivning
    LIST_ATTRS_TO_INCLUDE = Class SubClass beskrivning
    LIST_NAME = _antal
    -> ListElementCounter_3
ListElementCounter_3
    CNT_ATTR = antal
    LIST_NAME = _antal{}
    -> FeatureMerger_4 [REQUESTOR]
ListBuilder_13
    GROUP_BY = Class intrasis_name SubClass beskrivning
    LIST_ATTRS_TO_INCLUDE = Class intrasis_name SubClass beskrivning
    LIST_NAME = _list
    -> AttributeRemover_4
AttributeRemover_4
    LIST_ATTRS = _list{} _list{}.Class _list{}.SubClass _list{}.intrasis_name _list{}.beskrivning
    -> ListBuilder_14
ListBuilder_14
    GROUP_BY = Class SubClass beskrivning
    LIST_ATTRS_TO_INCLUDE = intrasis_name
    LIST_NAME = _list
    -> ListElementCounter_10
ListElementCounter_10
    CNT_ATTR = antal_intrasis_projekt
    LIST_NAME = _list{}
    -> FeatureMerger_4 [SUPPLIER]
FeatureMerger_4
    ATTR_ACCUM_MODE = Merge Supplier
    ATTR_CONFLICT_RES_LOOKUP = REQUESTOR_IF_CONFLICT
    CLEANING_TOLERANCE_LOOKUP = AUTO
    CONNECT_Z_MODE_LOOKUP = FIRST_WINS
    GEOM_TYPE_VAL = POLYGONS
    IGNORE_NULLS = No
    JOIN_KEYS = @Value(Class) @Value(Class) AUTO @Value(beskrivning) @Value(beskrivning) AUTO @Value(SubClass) @Value(SubClass) AUTO
    MERGE_COUNT_ATTR = antal_intrasis_projekt
    MERGE_TYPE = Attributes Only
    PROCESS_DUPS = YES
    REJECT_NULL_MISSING_KEYS = No
    SUPPLIERS_FIRST = No
    ATTR_CONFLICT_RES = Use Requestor
    CLEANING_TOLERANCE = Automatic
    CONNECT_Z_MODE = First Wins
    GEOM_TYPE = Build Polygons
    MERGED -> AttributeManager_3
AttributeManager_3
    ATTR_TABLE:
      REMOVE _antal{}.Class (buffer)
      REMOVE _antal{}.SubClass (buffer)
      REMOVE _antal{}.beskrivning (buffer)
      REMOVE _list{}.intrasis_name (buffer)
    -> unika_beskrivning (writer OGCGEOPACKAGE_2)
unika_beskrivning (writer OGCGEOPACKAGE_2)
    attributes: Class text, SubClass text, beskrivning text, antal int, antal_intrasis_projekt int
Tester_9
    BOOL_OP = OR
    TEST_CLAUSE = TEST tolkning ATTRIBUTE_HAS_A_VALUE ""
    TEST_MODE = TEST
    PASSED -> ListBuilder_4
    PASSED -> ListBuilder_11
ListBuilder_4
    GROUP_BY = Class SubClass tolkning
    LIST_ATTRS_TO_INCLUDE = Class SubClass tolkning
    LIST_NAME = _antal
    -> ListElementCounter_4
ListElementCounter_4
    CNT_ATTR = antal
    LIST_NAME = _antal{}
    -> FeatureMerger_5 [REQUESTOR]
ListBuilder_11
    GROUP_BY = Class intrasis_name SubClass tolkning
    LIST_ATTRS_TO_INCLUDE = Class intrasis_name SubClass tolkning
    LIST_NAME = _list
    -> AttributeRemover_3
AttributeRemover_3
    LIST_ATTRS = _list{} _list{}.Class _list{}.SubClass _list{}.intrasis_name _list{}.tolkning
    -> ListBuilder_12
ListBuilder_12
    GROUP_BY = Class SubClass tolkning
    LIST_ATTRS_TO_INCLUDE = intrasis_name
    LIST_NAME = _list
    -> ListElementCounter_9
ListElementCounter_9
    CNT_ATTR = antal_intrasis_projekt
    LIST_NAME = _list{}
    -> FeatureMerger_5 [SUPPLIER]
FeatureMerger_5
    ATTR_ACCUM_MODE = Merge Supplier
    ATTR_CONFLICT_RES_LOOKUP = REQUESTOR_IF_CONFLICT
    CLEANING_TOLERANCE_LOOKUP = AUTO
    CONNECT_Z_MODE_LOOKUP = FIRST_WINS
    GEOM_TYPE_VAL = POLYGONS
    IGNORE_NULLS = No
    JOIN_KEYS = @Value(Class) @Value(Class) AUTO @Value(tolkning) @Value(tolkning) AUTO @Value(SubClass) @Value(SubClass) AUTO
    MERGE_COUNT_ATTR = antal_intrasis_projekt
    MERGE_TYPE = Attributes Only
    PROCESS_DUPS = YES
    REJECT_NULL_MISSING_KEYS = No
    SUPPLIERS_FIRST = No
    ATTR_CONFLICT_RES = Use Requestor
    CLEANING_TOLERANCE = Automatic
    CONNECT_Z_MODE = First Wins
    GEOM_TYPE = Build Polygons
    MERGED -> AttributeManager_6
AttributeManager_6
    ATTR_TABLE:
      REMOVE _antal{}.Class (buffer)
      REMOVE _antal{}.SubClass (buffer)
      REMOVE _antal{}.tolkning (buffer)
      REMOVE _list{}.intrasis_name (buffer)
    -> unika_tolkning (writer OGCGEOPACKAGE_2)
unika_tolkning (writer OGCGEOPACKAGE_2)
    attributes: Class text, SubClass text, tolkning text, antal text(20), antal_intrasis_projekt text(20)
Tester_10
    BOOL_OP = OR
    TEST_CLAUSE = TEST tolkningsattribut ATTRIBUTE_HAS_A_VALUE ""
    TEST_MODE = TEST
    PASSED -> ListBuilder_5
    PASSED -> ListBuilder_9
ListBuilder_5
    GROUP_BY = Class SubClass tolkningsattribut
    LIST_ATTRS_TO_INCLUDE = Class SubClass tolkningsattribut
    LIST_NAME = _antal
    -> ListElementCounter_5
ListElementCounter_5
    CNT_ATTR = antal
    LIST_NAME = _antal{}
    -> FeatureMerger_6 [REQUESTOR]
ListBuilder_9
    GROUP_BY = Class intrasis_name SubClass tolkningsattribut
    LIST_ATTRS_TO_INCLUDE = Class intrasis_name SubClass tolkningsattribut
    LIST_NAME = _list
    -> AttributeRemover_2
AttributeRemover_2
    LIST_ATTRS = _list{} _list{}.Class _list{}.SubClass _list{}.intrasis_name _list{}.tolkningsattribut
    -> ListBuilder_10
ListBuilder_10
    GROUP_BY = Class SubClass tolkningsattribut
    LIST_ATTRS_TO_INCLUDE = intrasis_name
    LIST_NAME = _list
    -> ListElementCounter_8
ListElementCounter_8
    CNT_ATTR = antal_intrasis_projekt
    LIST_NAME = _list{}
    -> FeatureMerger_6 [SUPPLIER]
FeatureMerger_6
    ATTR_ACCUM_MODE = Merge Supplier
    ATTR_CONFLICT_RES_LOOKUP = REQUESTOR_IF_CONFLICT
    CLEANING_TOLERANCE_LOOKUP = AUTO
    CONNECT_Z_MODE_LOOKUP = FIRST_WINS
    GEOM_TYPE_VAL = POLYGONS
    IGNORE_NULLS = No
    JOIN_KEYS = @Value(Class) @Value(Class) AUTO @Value(tolkningsattribut) @Value(tolkningsattribut) AUTO @Value(SubClass) @Value(SubClass) AUTO
    MERGE_COUNT_ATTR = antal_intrasis_projekt
    MERGE_TYPE = Attributes Only
    PROCESS_DUPS = YES
    REJECT_NULL_MISSING_KEYS = No
    SUPPLIERS_FIRST = No
    ATTR_CONFLICT_RES = Use Requestor
    CLEANING_TOLERANCE = Automatic
    CONNECT_Z_MODE = First Wins
    GEOM_TYPE = Build Polygons
    MERGED -> AttributeManager_4
AttributeManager_4
    ATTR_TABLE:
      REMOVE _antal{}.Class (buffer)
      REMOVE _antal{}.SubClass (buffer)
      REMOVE _antal{}.tolkningsattribut (buffer)
      REMOVE _list{}.intrasis_name (buffer)
    -> unika_tolkningsattribut (writer OGCGEOPACKAGE_2)
unika_tolkningsattribut (writer OGCGEOPACKAGE_2)
    attributes: Class text, SubClass text, tolkningsattribut text, antal text(20), antal_intrasis_projekt text(20)
Tester_2
    BOOL_OP = OR
    TEST_CLAUSE = TEST undertyp ATTRIBUTE_HAS_A_VALUE ""
    TEST_MODE = TEST
    PASSED -> ListBuilder_6
    PASSED -> ListBuilder_7
ListBuilder_6
    GROUP_BY = Class SubClass undertyp
    LIST_ATTRS_TO_INCLUDE = Class SubClass undertyp
    LIST_NAME = _antal
    -> ListElementCounter_6
ListElementCounter_6
    CNT_ATTR = antal
    LIST_NAME = _antal{}
    -> FeatureMerger_7 [REQUESTOR]
ListBuilder_7
    GROUP_BY = Class intrasis_name SubClass undertyp
    LIST_ATTRS_TO_INCLUDE = Class intrasis_name SubClass undertyp
    LIST_NAME = _list
    -> AttributeRemover
AttributeRemover
    LIST_ATTRS = _list{} _list{}.Class _list{}.SubClass _list{}.intrasis_name _list{}.undertyp
    -> ListBuilder_8
ListBuilder_8
    GROUP_BY = Class SubClass undertyp
    LIST_ATTRS_TO_INCLUDE = intrasis_name
    LIST_NAME = _list
    -> ListElementCounter_7
ListElementCounter_7
    CNT_ATTR = antal_intrasis_projekt
    LIST_NAME = _list{}
    -> FeatureMerger_7 [SUPPLIER]
FeatureMerger_7
    ATTR_ACCUM_MODE = Merge Supplier
    ATTR_CONFLICT_RES_LOOKUP = REQUESTOR_IF_CONFLICT
    IGNORE_NULLS = No
    JOIN_KEYS = @Value(Class) @Value(Class) AUTO @Value(undertyp) @Value(undertyp) AUTO @Value(SubClass) @Value(SubClass) AUTO
    MERGE_TYPE = Attributes Only
    PROCESS_DUPS = NO
    REJECT_NULL_MISSING_KEYS = No
    SUPPLIERS_FIRST = No
    ATTR_CONFLICT_RES = Use Requestor
    MERGED -> AttributeManager_5
AttributeManager_5
    ATTR_TABLE:
      REMOVE _antal{}.Class (buffer)
      REMOVE _antal{}.SubClass (buffer)
      REMOVE _antal{}.undertyp (buffer)
      REMOVE _list{}.intrasis_name (buffer)
    -> unika_undertyp (writer OGCGEOPACKAGE_2)
unika_undertyp (writer OGCGEOPACKAGE_2)
    attributes: Class text, SubClass text, undertyp text, antal text(20), antal_intrasis_projekt text(20)
