FME workspace lagg_ihop_agg_filer.fmw

Parameters:
- SourceDataset_PATH = C:\ny_slask\test_agg_all\alla_intrasis\publicerade\gpkg   # INCLUDE_WEB_BROWSER Source Folder and File Pathnames Folder
- SourceDataset_PATH_3 = C:\ny_slask\test_agg_all\alla_intrasis   # INCLUDE_WEB_BROWSER Source Folder and File Pathnames Folder
- DestDataset_OGCGEOPACKAGE = $(SourceDataset_PATH)\agg_add.gpkg   # GeoPackage File
- DestDataset_XLSXW = $(SourceDataset_PATH)\agg_add.xslx   # Destination Microsoft Excel File
- DestDataset_CSV2 = $(SourceDataset_PATH)   # Destination CSV (Comma Separated Value) Folder

Readers:
- PATH_2: PATH from $(SourceDataset_PATH_3)

Writers:
- OGCGEOPACKAGE_1: OGCGEOPACKAGE to $(DestDataset_OGCGEOPACKAGE)
- XLSXW_1: XLSXW to $(DestDataset_XLSXW)
- CSV2_1: CSV2 to $(DestDataset_CSV2)

PATH (reader PATH_2)
    attributes: path_unix buffer, path_windows buffer, path_rootname buffer, path_filename buffer, path_extension buffer, path_directory_unix buffer, path_directory_windows buffer, path_type char(10)
    -> FeatureReader_3 [INITIATOR]
FeatureReader_3
    ATTRIBUTES = fynd_etc,"intrasis_dbname,swedigarch_id,IntrasisId,Name,Class,SubClass,Color,geometry_count,attributes,anmärkning,antal,art,bergart,beskrivning,botten,bottentyp,bredd,bruksspår,bränd,buk,datering,dekor,dekorkomposition,e_del,element,f_grad,flerfaldigt_bearbetad,form,formelement,fragmenteringsgrad,frostsprängd,fyndenhetsnummer,fyndnummer,fyndstatus,godstyp,grepp,hals,huvudtyp,kommentar,kärldel,kärltyp,kön,lager,linjeorientering,längd,längdd,magring,material,metall,mynning,mynningsform,mynningsrand,mynningstyp,myntbestämning,nisp,odefinierad_del,osäker,patinerad,provnummer,påverkan,rad/linjetyp,rörskaft,sakord,sida,skuldra,skärvtjocklek,spår,status,stick,största_korn,teknik,text,tjocklek,typ,undertyp,undertyp_yta,vikt,volym,yngsta_datering,yta,ytbehandling,yttre_mynningsrand,yttyp,äldsta_datering,ålder,öra,övrigt,id",objects,"intrasis_dbname,swedigarch_id,IntrasisId,Name,Class,SubClass,Color,geometry_count,attributes,anmärkning,anvädningsfas,aska,beskrivning,botten,bredd,bränd_lera,datering,diameter,dimensioner,djup,djurben,fethet,filnamn,form,fotodatum,fotograf,från,fyllningskaraktär,fyllningsmaterial,fyndinsamlingsmetod,färg,hägnadstyp,höjd,innehåll,innehåller_fyllningar,kalk,kalkbruk,kol,kompakthet,konstruktionsdetalj,konstruktionselement,kontaktyta,lagerbegränsning,lerfläckar,lerkladdar,lerklining,längd,material,materialstorlek,medium,metod,minsta_tjocklek,motiv,motivtyp,mätvärdesnr.,notering,orientering,sida,skörbränd_sten,småsten,sot,stenskoning,stick,stolpfärgning,storlek,största_tjocklek,sökväg,tegelbrockor,tegelkross,teknik,tolkning,träbitar,träflis,träkol,typ,typ_av_aktivitet,undersökningsmetod,undersökt,undersökt_andel,undertyp,veckonummer,x,y,övrigt,id"
    ATTR_ACCUM_MODE = Only Use Result
    CLIP_TO_ENVELOPE = NO
    COMBINE_GEOM = Use Result
    DATASET = @Value(path_windows)
    FORMAT = OGCGEOPACKAGE
    INITIATOR_FIRST_OUTPUT = default
    INTERACT = NONE
    OGCGEOPACKAGE_ENCODE_FEATURE_TYPE_AND_ATTR_NAMES = YES
    OGCGEOPACKAGE_ENFORCE_FOREIGN_KEY_INTEGRITY = NO
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = NO
    OGCGEOPACKAGE_READ_BOOLEANS_AS_YES_NO = YES
    OGCGEOPACKAGE_READ_NULLS = YES
    OGCGEOPACKAGE_USE_SEARCH_ENVELOPE = NO
    ORDER_RESULTS = No
    OUTPUT_ADD_SCHEMA_ATTRIBUTES = YES
    OUTPUT_FEATURES_DISPLAY = Schema and Data Features
    OUTPUT_USE_SCHEMA_CACHE = NO
    READER_BEHAVIOR = SELECTFEATTYPES
    <OTHER> -> Tester
Note: Tester [Tester] / Test Clauses: Left ValueOperatorRight Value@Value(fme_feature_type_name)=objectsAdvanced: / Preserve Feature Order: Per Output Port
Tester
    BOOL_OP = OR
    TEST_CLAUSE = TEST @Value(fme_feature_type_name) = objects
    TEST_MODE = TEST
    PASSED -> SchemaScanner_2
    FAILED -> SchemaScanner_3
SchemaScanner_2
    CASE = No
    EMPTY_ATTR_HANDLING = IGNORE
    HOLD = Yes
    IGNORE_REGEXP = ^fme_<pipe>^multi_<pipe>^attribute{
    INCLUDE_FORMAT_ATTR = No
    NUMERIC_ALLOW_LEADING_ZEROES = Yes
    SCHEMA_NAME_ATTR = fme_feature_type_name
    TEST_STRING = Enter a string to test here...
    UNBOUNDED_NUMBERS = Yes
    UNBOUNDED_STRINGS = No
    -> File100 (writer CSV2_1)
    -> objects (writer OGCGEOPACKAGE_1)
    <SCHEMA> -> File100 (writer CSV2_1)
    <SCHEMA> -> objects (writer OGCGEOPACKAGE_1)
Note: (2): test_adder [OGCGEOPACKAGE]- objects
objects (writer OGCGEOPACKAGE_1)
Note: : alla_ej_publicerade [CSV2]
File100 (writer CSV2_1)
SchemaScanner_3
    CASE = No
    EMPTY_ATTR_HANDLING = IGNORE
    HOLD = Yes
    IGNORE_REGEXP = ^fme_<pipe>^multi_
    INCLUDE_FORMAT_ATTR = No
    NUMERIC_ALLOW_LEADING_ZEROES = Yes
    SCHEMA_NAME_ATTR = fme_feature_type_name
    UNBOUNDED_NUMBERS = Yes
    UNBOUNDED_STRINGS = No
    -> File1 (writer CSV2_1)
    -> fynd_etc (writer OGCGEOPACKAGE_1)
    <SCHEMA> -> File1 (writer CSV2_1)
    <SCHEMA> -> fynd_etc (writer OGCGEOPACKAGE_1)
Note: : agg_add [OGCGEOPACKAGE]
fynd_etc (writer OGCGEOPACKAGE_1)
File1 (writer CSV2_1)
Note: : test_adder [XLSXW]
Sheet100 (writer XLSXW_1) [off]
Note: : test_adder [XLSXW]
Sheet1 (writer XLSXW_1) [off]
