FME workspace aggregate_intrasis_siteworks_runner.fmw

Parameters:
- SourceDataset_PATH = C:\ny_slask\test_agg_all\liten_mapp   # INCLUDE_WEB_BROWSER Source Folder and File Pathnames Folder

Readers:
- PATH_1: PATH from $(SourceDataset_PATH)

PATH (reader PATH_1)
    attributes: path_unix buffer, path_windows buffer, path_rootname buffer, path_filename buffer, path_extension buffer, path_directory_unix buffer, path_directory_windows buffer, path_type char(10)
    -> Tester
Tester
    BOOL_OP = OR
    TEST_CLAUSE:
      CASE_INSENSITIVE_TEST @Value(path_filename) BEGINS_WITH agg
      CASE_INSENSITIVE_TEST @Value(path_filename) BEGINS_WITH check
      CASE_INSENSITIVE_TEST @Value(path_filename) BEGINS_WITH test
    TEST_MODE = CASE_INSENSITIVE_TEST
    FAILED -> WorkspaceRunner
WorkspaceRunner
    BLOCKING = Yes
    OVERWRITE_LOG_FILE = HONOR
    STDERR_HANDLING = COMBINE
    WORKSPACE_FILE = $(FME_MF_DIR_ENCODED)aggregate_intrasis_siteworks.fmw
    WORKSPACE_PARAMETERS = SourceDataset_OGCGEOPACKAGE,@Value(path_windows),DestDataset_OGCGEOPACKAGE,@Value(path_directory_windows)aggregated.gpkg
