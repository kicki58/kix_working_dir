FME workspace third_try.fmw

Parameters:
- SourceDataset_JSON_3 = C:\ny_slask\open_refine\openrefine_changes_22okt.json   # Source JSON (JavaScript Object Notation) File or URL
- SourceDataset_CSV2_3 = C:\ny_slask\open_refine\StruckeC14_Sweden_openrefine1.csv   # Source CSV (Comma Separated Value) File(s)
- SourceDataset_CSV2 = C:\ny_slask\open_refine\StruckeC14_Sweden_orig.csv   # Source CSV (Comma Separated Value) File(s)

Readers:
- JSON_1: JSON from $(SourceDataset_JSON_3)
- CSV2_1: CSV2 from $(SourceDataset_CSV2)
- CSV2_2: CSV2 from $(SourceDataset_CSV2_3)

JSONFeature (reader JSON_1)
    attributes: op string, engineConfig.mode string, columnName string, expression string, onError string, repeat boolean, repeatCount int, description string, edits{}.from{} string, edits{}.fromBlank boolean, edits{}.fromError boolean, edits{}.to string, engineConfig.facets{}.type string, engineConfig.facets{}.name string, engineConfig.facets{}.columnName string, engineConfig.facets{}.query string, engineConfig.facets{}.mode string, engineConfig.facets{}.caseSensitive boolean, engineConfig.facets{}.invert boolean
    -> Counter
Counter
    CNT_ATTR = _count
    DOMAIN = counter
    SCOPE = Global
    SHOW_ERROR_INDICATORS = No
    START = 0
    -> AttributeManager_2
AttributeManager_2
    SHOW_ERROR_INDICATORS = No
    -> ListExploder
ListExploder
    ATTR_CONFLICT_RES_LOOKUP = INCOMING_IF_CONFLICT
    INDEX_ATTR = _element_index_edits
    LIST_ATTR = edits{}
    SHOW_ERROR_INDICATORS = No
    ATTR_ACCUM_MODE = Merge List Attributes
    ATTR_CONFLICT_RES = Use List Attribute Values
    ELEMENTS -> AttributeFilter_2
AttributeFilter_2
    ATTR_NAME = columnName
    ATTR_VALUES = <Empty>,<Missing>,<Null>,<Unfiltered>,context_type,site_type,socken,species
    SHOW_ERROR_INDICATORS = No
    site_type -> ListExploder_2
ListExploder_2
    ATTR_CONFLICT_RES_LOOKUP = INCOMING_IF_CONFLICT
    INDEX_ATTR = _element_index_from
    LIST_ATTR = from{}
    SHOW_ERROR_INDICATORS = No
    ATTR_ACCUM_MODE = Merge List Attributes
    ATTR_CONFLICT_RES = Use List Attribute Values
    ELEMENTS -> AttributeFilter
AttributeFilter
    ATTR_NAME = columnName
    ATTR_VALUES = <Empty>,<Missing>,<Null>,<Unfiltered>,context_type,site_type,socken,species
    SHOW_ERROR_INDICATORS = No
    site_type -> Tester_2
    site_type -> DuplicateFilter_2
DuplicateFilter_2
    INPUT_ORDERED_CHOICE_LOOKUP = NO
    KEYATTR = from
    SHOW_ERROR_INDICATORS = No
    INPUT_ORDERED_CHOICE = No
    UNIQUE -> FeatureMerger [SUPPLIER]
    UNIQUE -> FeatureMerger_3 [SUPPLIER]
    DUPLICATE -> BulkAttributeRenamer_3
BulkAttributeRenamer_3
    ATTRCHOICE_ACTION = NONPROTECTEDFME
    MODE_CHOICE = RENAME
    PATTERN_ACTION_DISP = ADDPREFIX
    REPLACE_STR = dupl_
    SHOW_ERROR_INDICATORS = No
    ATTRCHOICE = All Attributes
    -> FeatureMerger_3 [REQUESTOR]
FeatureMerger_3
    ATTR_ACCUM_MODE = Merge Supplier
    ATTR_CONFLICT_RES_LOOKUP = REQUESTOR_IF_CONFLICT
    IGNORE_NULLS = No
    JOIN_KEYS = @Value(dupl_from) @Value(from) AUTO
    MERGE_TYPE_VAL = ATTRIBUTES
    PROCESS_DUPS = NO
    REJECT_NULL_MISSING_KEYS = No
    SHOW_ERROR_INDICATORS = No
    SUPPLIERS_FIRST = No
    ATTR_CONFLICT_RES = Use Requestor
    MERGE_TYPE = Merge Attributes
    MERGED -> AttributeRemover_2
AttributeRemover_2
    REMOVE_ATTRS = columnName,description,dupl_columnName,dupl_description,dupl_engineConfig.mode,dupl_expression,dupl_fromBlank,dupl_fromError,dupl_onError,dupl_op,dupl_repeat,dupl_repeatCount,engineConfig.mode,expression,fromBlank,fromError,onError,op,repeat,repeatCount
    SHOW_ERROR_INDICATORS = No
Tester_2
    BOOL_OP = OR
    SHOW_ERROR_INDICATORS = No
    TEST_CLAUSE = CASE_INSENSITIVE_TEST @Value(from) CONTAINS kapell
    TEST_MODE = CASE_INSENSITIVE_TEST
    PASSED -> Sorter
Sorter
    SHOW_ERROR_INDICATORS = No
    SORT_PARM = _count NUMERIC ASCENDING NON_VALUES_AFTER_VALUES _element_index_edits NUMERIC ASCENDING NON_VALUES_AFTER_VALUES
CSV (reader CSV2_1)
    attributes: fid uint32, socken varchar(20), landskap varchar(15), place_name varchar(51), raa_id varchar(26), site_type varchar(55), site_id varchar(46), uppdragsnummer varchar(20), lab_id varchar(21), c14_age_bp uint32, c14_error uint32, d13C real32, pMC_value real32, pMC_error real32, c14_data_status varchar(41), comment varchar(215), assessed_relevant varchar(1), material varchar(28), species varchar(40), context_id varchar(22), context_type varchar(44), northing_3006 uint32, easting_3006 uint32, longitude real64, latitude real64, location_precision varchar(19), cal_68_min int32, cal_68_max int32, cal_95_min int32, cal_95_max int32,
      median_cal_year int32, calibration_method varchar(28), calibration_status varchar(16), author varchar(118), publication_year uint32, title varchar(470), journal varchar(183), place_of_publication varchar(28)
    -> StringCaseChanger
StringCaseChanger
    ATTRCHOICE = SELECTED
    ATTRLIST = site_type
    CHANGE_TYPE = lower
    SHOW_ERROR_INDICATORS = No
    -> FeatureMerger [REQUESTOR]
FeatureMerger
    ATTR_ACCUM_MODE = Merge Supplier
    ATTR_CONFLICT_RES_LOOKUP = REQUESTOR_IF_CONFLICT
    IGNORE_NULLS = No
    JOIN_KEYS = @Value(site_type) @Value(from) AUTO
    MERGE_TYPE_VAL = ATTRIBUTES
    PROCESS_DUPS = NO
    REJECT_NULL_MISSING_KEYS = No
    SHOW_ERROR_INDICATORS = No
    SUPPLIERS_FIRST = No
    ATTR_CONFLICT_RES = Use Requestor
    MERGE_TYPE = Merge Attributes
    MERGED -> AttributeManager
    UNMERGED_REQUESTOR -> BulkAttributeRenamer
AttributeManager
    ATTR_TABLE:
      SET_TO site_id (varchar(46)) = @Value(to)
      REMOVE engineConfig.facets{}.type (buffer)
      REMOVE engineConfig.facets{}.name (buffer)
      REMOVE engineConfig.facets{}.columnName (buffer)
      REMOVE engineConfig.facets{}.query (buffer)
      REMOVE engineConfig.facets{}.mode (buffer)
      REMOVE engineConfig.facets{}.caseSensitive (logical)
      REMOVE engineConfig.facets{}.invert (logical)
      REMOVE fromBlank (logical)
      REMOVE fromError (logical)
    SHOW_ERROR_INDICATORS = No
    -> BulkAttributeRenamer
BulkAttributeRenamer
    ATTRCHOICE_ACTION = NONPROTECTEDFME
    MODE_CHOICE = RENAME
    PATTERN_ACTION_DISP = ADDPREFIX
    REPLACE_STR = org_
    SHOW_ERROR_INDICATORS = No
    ATTRCHOICE = All Attributes
    -> FeatureMerger_2 [SUPPLIER]
CSV (reader CSV2_2)
    attributes: fid uint32, socken varchar(20), landskap varchar(15), place_name varchar(51), raa_id varchar(26), site_type varchar(55), site_id varchar(46), uppdragsnummer varchar(20), lab_id varchar(21), c14_age_bp uint32, c14_error uint32, d13C real32, pMC_value real32, pMC_error real32, c14_data_status varchar(41), comment varchar(215), assessed_relevant varchar(1), material varchar(28), species varchar(40), context_id varchar(22), context_type varchar(44), northing_3006 uint32, easting_3006 uint32, longitude real64, latitude real64, location_precision varchar(19), cal_68_min int32, cal_68_max int32, cal_95_min int32, cal_95_max int32,
      median_cal_year int32, calibration_method varchar(28), calibration_status varchar(16), author varchar(118), publication_year uint32, title varchar(470), journal varchar(183), place_of_publication varchar(28)
    -> BulkAttributeRenamer_2
BulkAttributeRenamer_2
    ATTRCHOICE_ACTION = NONPROTECTEDFME
    MODE_CHOICE = RENAME
    PATTERN_ACTION_DISP = ADDPREFIX
    REPLACE_STR = openrefine_
    SHOW_ERROR_INDICATORS = No
    ATTRCHOICE = All Attributes
    -> FeatureMerger_2 [REQUESTOR]
FeatureMerger_2
    ATTR_ACCUM_MODE = Merge Supplier
    ATTR_CONFLICT_RES_LOOKUP = REQUESTOR_IF_CONFLICT
    IGNORE_NULLS = No
    JOIN_KEYS = @Value(openrefine_fid) @Value(org_fid) AUTO
    MERGE_TYPE_VAL = ATTRIBUTES
    PROCESS_DUPS = NO
    REJECT_NULL_MISSING_KEYS = No
    SHOW_ERROR_INDICATORS = No
    SUPPLIERS_FIRST = No
    ATTR_CONFLICT_RES = Use Requestor
    MERGE_TYPE = Merge Attributes
    MERGED -> AttributeRemover
AttributeRemover
    REMOVE_ATTRS = openrefine_assessed_relevant,openrefine_author,openrefine_c14_age_bp,openrefine_c14_data_status,openrefine_c14_error,openrefine_cal_68_max,openrefine_cal_68_min,openrefine_cal_95_max,openrefine_cal_95_min,openrefine_calibration_method,openrefine_calibration_status,openrefine_comment,openrefine_context_id,openrefine_context_type,openrefine_d13C,openrefine_easting_3006,openrefine_fid,openrefine_journal,openrefine_lab_id,openrefine_landskap,openrefine_latitude,openrefine_location_precision,openrefine_longitude,openrefine_material,openrefine_median_cal_year,openrefine_northing_3006,openrefine_pMC_error,openrefine_pMC_value,openrefine_place_name,openrefine_place_of_publication,openrefine_publication_year,openrefine_raa_id,openrefine_socken,openrefine_species,openrefine_title,openrefine_uppdragsnummer,org__element_index_edits,org__element_index_from,org_assessed_relevant,org_author,org_c14_age_bp,org_c14_data_status,org_c14_error,org_cal_68_max,org_cal_68_min,org_cal_95_max,org_cal_95_min,org_calibration_method,org_calibration_status,org_columnName,org_comment,org_context_id,org_context_type,org_d13C,org_description,org_easting_3006,org_engineConfig.mode,org_expression,org_fid,org_from,org_journal,org_lab_id,org_landskap,org_latitude,org_location_precision,org_longitude,org_material,org_median_cal_year,org_northing_3006,org_onError,org_op,org_pMC_error,org_pMC_value,org_place_name,org_place_of_publication,org_publication_year,org_raa_id,org_repeat,org_repeatCount,org_socken,org_species,org_title,org_to,org_uppdragsnummer,openrefine_site_id,org_site_id
    SHOW_ERROR_INDICATORS = No
    -> Tester
Tester
    BOOL_OP = OR
    SHOW_ERROR_INDICATORS = No
    TEST_CLAUSE = TEST @Value(openrefine_site_type) = @Value(org_site_type)
    TEST_MODE = TEST
    FAILED -> DuplicateFilter
    FAILED -> DuplicateFilter_3
    FAILED -> DuplicateFilter_4
DuplicateFilter
    INPUT_ORDERED_CHOICE_LOOKUP = NO
    KEYATTR = openrefine_site_type org_site_type
    SHOW_ERROR_INDICATORS = No
    INPUT_ORDERED_CHOICE = No
DuplicateFilter_3
    INPUT_ORDERED_CHOICE_LOOKUP = NO
    KEYATTR = org_site_type
    SHOW_ERROR_INDICATORS = No
    INPUT_ORDERED_CHOICE = No
DuplicateFilter_4
    INPUT_ORDERED_CHOICE_LOOKUP = NO
    KEYATTR = openrefine_site_type
    SHOW_ERROR_INDICATORS = No
    INPUT_ORDERED_CHOICE = No
