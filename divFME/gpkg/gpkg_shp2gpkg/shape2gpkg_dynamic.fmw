FME workspace shape2gpkg_dynamic.fmw

Parameters:
- SourceDataset_PATH = C:\ny_slask\xlm\ej_intrasis\Åsbo_510617   # INCLUDE_WEB_BROWSER Source Folder and File Pathnames Folder
- DestDataset_OGCGEOPACKAGE = C:\ny_slask\xlm\ej_intrasis\Åsbo_510617.gpkg   # GeoPackage File
- PATH_IN_RECURSE_DIRECTORIES_PATH_2 = YES   # Recurse Into Subfolders
- COORDSYS = EPSG:3006   # Coordinate System

Readers:
- PATH_1: PATH from $(SourceDataset_PATH)

Writers:
- OGCGEOPACKAGE_1: OGCGEOPACKAGE to $(DestDataset_OGCGEOPACKAGE)

PATH (reader PATH_1)
    attributes: path_unix buffer, path_windows buffer, path_rootname buffer, path_filename buffer, path_extension buffer, path_directory_unix buffer, path_directory_windows buffer, path_type char(10)
    -> FeatureReader [INITIATOR]
FeatureReader
    ATTR_ACCUM_MODE = Only Use Result
    COMBINE_GEOM = Use Result
    DATASET = @Value(path_windows)
    FORMAT = SHAPEFILE
    INTERACT = NONE
    ORDER_RESULTS = No
    OUTPUT_ADD_SCHEMA_ATTRIBUTES = NO
    OUTPUT_FEATURES_DISPLAY = Schema and Data Features
    SHAPEFILE_ALLOW_MISMATCHED_SHZ_BASENAME = No
    SHAPEFILE_DONUT_DETECTION = ORIENTATION
    SHAPEFILE_ENCODING = fme-source-encoding
    SHAPEFILE_MEASURES_AS_Z = No
    SHAPEFILE_NUMERIC_TYPE_ATTRIBUTE_HANDLING = STANDARD_TYPES
    SHAPEFILE_READ_BLANK_AS = MISSING
    SHAPEFILE_READ_NUMERIC_PADDING_AS = ZERO
    SHAPEFILE_REPORT_BAD_GEOMETRY = No
    SHAPEFILE_TRIM_PRECEDING_SPACES = Yes
    SHAPEFILE_USE_SEARCH_ENVELOPE = NO
    SHAPEFILE_USE_STRING_FOR_NUMERIC_STORAGE = No
    <SCHEMA> -> Table1 (writer OGCGEOPACKAGE_1)
    <OTHER> -> AttributeExposer
AttributeExposer
    ATTR_TABLE = fme_feature_type,,fme_template_feature_type,
    -> AttributeManager
AttributeManager
    -> CoordinateSystemSetter
CoordinateSystemSetter
    COORDSYS = $(COORDSYS)
    -> Table1 (writer OGCGEOPACKAGE_1)
Table1 (writer OGCGEOPACKAGE_1)
