FME workspace projinfo2editgpkg.fmw

Parameters:
- DestDataset_OGCGEOPACKAGE = C:\ny_slask\mm_intrasis2ages\mm2ages_register_2.gpkg   # GeoPackage File
- SourceDataset_SHAPEFILE = C:\ny_slask\GIS-data\socknar_sverige\socken\socknar_sverige.shp   # Source Esri Shapefile(s)
- SourceDataset_OGCGEOPACKAGE_2 = C:\ny_slask\GIS-data\kommun-lan-rike_1990\kommun-lan-rike_1990.gpkg   # GeoPackage File
- SourceDataset_PATH = C:\ny_slask\mm_intrasis2ages\gpkg_intrasis   # INCLUDE_WEB_BROWSER Source Folder and File Pathnames Folder
- MAX_FEATURES =   # Max Features to Read
- SourceDataset_OGCGEOPACKAGE_5 = C:\ny_slask\GIS-data\arkeologiska_uppdrag_undersökningsområden_sverige (9).gpkg   # GeoPackage File

Readers:
- SHAPEFILE_1: SHAPEFILE from $(SourceDataset_SHAPEFILE) in EPSG:3006
- OGCGEOPACKAGE_3: OGCGEOPACKAGE from $(SourceDataset_OGCGEOPACKAGE_2) in EPSG:3006
- PATH_1: PATH from $(SourceDataset_PATH) in EPSG:3006
- OGCGEOPACKAGE_4: OGCGEOPACKAGE from $(SourceDataset_OGCGEOPACKAGE_5) in EPSG:3006

Writers:
- OGCGEOPACKAGE_2: OGCGEOPACKAGE to $(DestDataset_OGCGEOPACKAGE) in EPSG:3006

PATH (reader PATH_1)
    attributes: path_unix buffer, path_windows buffer, path_rootname buffer, path_filename buffer, path_extension buffer, path_directory_unix buffer, path_directory_windows buffer, path_type char(10)
    -> Tester
Tester
    BOOL_OP = OR
    TEST_CLAUSE = CASE_INSENSITIVE_TEST @Value(path_filename) BEGINS_WITH agg
    TEST_MODE = CASE_INSENSITIVE_TEST
    FAILED -> FeatureReader [INITIATOR]
FeatureReader
    ATTRIBUTES = Multipoint,"fid,IntrasisId,object_id,Name,Class,SubClass,SymbolId,GeoObjectId,spatial_type",Point,"fid,IntrasisId,object_id,Name,Class,SubClass,SymbolId,GeoObjectId,spatial_type",Polygon,"fid,IntrasisId,object_id,Name,Class,SubClass,SymbolId,GeoObjectId,spatial_type",Polyline,"fid,IntrasisId,object_id,Name,Class,SubClass,SymbolId,GeoObjectId,spatial_type",attribute_relations,"related_id,base_id,id",attributes,"object_id,attribute_label,attribute_value,attribute_unit,class,data_type,attribute_id",features,"geom,object_id,SymbolId,GeoObjectId,spatial_type,fid",layer_styles,"f_table_catalog,f_table_schema,f_table_name,f_geometry_column,styleName,styleQML,styleSLD,useAsDefault,description,owner,ui,update_time,id",object_relations,"base_id,related_id,base_text,related_text,id",objects,"IntrasisId,Name,Class,SubClass,Color,geometry_count,attributes,object_id",project_information,"pk,SiteId,Plats,""Lst Dnr"",""Raä Dnr"",Inventarienummer,Projektkod,Projektnamn,Projektledare,Uppdragsgivare,Exploateringstyp,Undersökningstyp,Slutdatum,Beskrivning,fid"
    ATTR_ACCUM_MODE = Merge Initiator and Result
    ATTR_CONFLICT_RES = Use Result
    ATTR_IGNORE_NULLS = No
    CLIP_TO_ENVELOPE = NO
    COMBINE_GEOM = Use Result
    COORDSYS = EPSG:3006
    DATASET = @Value(path_windows)
    FEATURETYPES = project_information
    FORMAT = OGCGEOPACKAGE
    GEOMETRY_TYPES = Multipoint,"""geom,fme_point""",Point,"""geom,fme_point""",Polygon,"""geom,fme_area""",Polyline,"""geom,fme_line""",project_information,"""geom,fme_point"""
    INITIATOR_FIRST_OUTPUT = default
    INTERACT = NONE
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = NO
    OGCGEOPACKAGE_READ_BOOLEANS_AS_YES_NO = YES
    OGCGEOPACKAGE_READ_NULLS = YES
    OGCGEOPACKAGE_USE_SEARCH_ENVELOPE = NO
    ORDER_RESULTS = No
    OUTPUT_ADD_SCHEMA_ATTRIBUTES = NO
    OUTPUT_FEATURES_DISPLAY = Schema and Data Features
    OUTPUT_USE_SCHEMA_CACHE = YES
    READER_BEHAVIOR = SELECTFEATTYPES
    project_information -> AttributeManager_6
AttributeManager_6
    ATTR_TABLE:
      RENAME_SET_VALUE path_rootname > gpkg_name (buffer)
      SET_TO uppdragsnummer (varchar(6)) = saknas
      SET_TO beslutande_myndighet (varchar(200))
      SET_TO beslutsdatum (varchar(200))
      RENAME_SET_VALUE Lst Dnr > diarienummer (buffer)
      SET_TO uppdragstyp (varchar(200))
      RENAME_SET_VALUE Undersökningstyp > uppdragstyp (buffer)
      SET_TO utforande_organisation (varchar(12)) = Malmö museer
      SET_TO nollresultat (varchar(200))
      SET_TO url (varchar(6)) = saknas
      SET_TO status (varchar(200))
      REMOVE pk (int32)
      REMOVE SiteId (buffer)
      REMOVE Plats (buffer)
      REMOVE Raä Dnr (buffer)
      REMOVE Inventarienummer (buffer)
      REMOVE Projektkod (buffer)
      REMOVE Projektnamn (buffer)
      REMOVE Projektledare (buffer)
      REMOVE Uppdragsgivare (buffer)
      REMOVE Exploateringstyp (buffer)
      REMOVE Slutdatum (buffer)
      REMOVE Beskrivning (buffer)
      REMOVE fid (int64)
      REMOVE path_unix (buffer)
      REMOVE path_windows (buffer)
      REMOVE path_filename (buffer)
      REMOVE path_extension (buffer)
      REMOVE path_directory_unix (buffer)
      REMOVE path_directory_windows (buffer)
      REMOVE path_type (varchar(10))
    USER_EXPOSED_ATTRIBUTES = path_rootname
    -> SpatialFilter [Candidate]
AttributeRemover_2
    REMOVE_ATTRS = beslutatnamn,enhetstyp,gransstatus,hogstaforvaltningsniva,id,kommunkod,landareal_enhet,landareal_varde,landskod,lanskod,objektidentitet,objekttyp,objektversion,referensdatumfran,referensdatumtill,totalareal_enhet,totalareal_varde,vattenareal_enhet,vattenareal_varde,versiongiltigfran,versiongiltigtill
    -> AttributeManager_2
AttributeManager_2
    ATTR_TABLE = RENAME_SET_VALUE namnkortform > kommun (buffer)
    -> SpatialFilter [Filter]
    -> kommun_namn (writer OGCGEOPACKAGE_2)
SpatialFilter
    AGGREGATE_HANDLING = Yes
    ATTR_CONFLICT_RES_LOOKUP = CANDIDATE_IF_CONFLICT
    BOOL_OP = OR
    BOUNDING_BOX = NO
    CURVE_BOUNDARY_RULE = ENDPOINTS_MOD2
    MULTI_BASE = YES
    PREDATTR = _predicate
    PREDICATES = INTERSECTS
    ATTR_ACCUM_MODE = Merge Filter
    ATTR_CONFLICT_RES = Use Candidate
    BASE_TYPE = Multiple Filters
    CURVE_BOUNDARY_RULE_PARAM = Default Rule
    PASS_CRITERIA = Pass Against One Filter
    USE_BOUNDING_BOX = No
    PASSED -> SpatialFilter_2 [Candidate]
kommun_namn (writer OGCGEOPACKAGE_2)
    attributes: kommun text
AttributeRemover_3
    REMOVE_ATTRS = beslutatnamn,enhetstyp,gransstatus,hogstaforvaltningsniva,id,landareal_enhet,landareal_varde,landskod,lansbokstav,lanskod,objektidentitet,objekttyp,objektversion,referensdatumfran,referensdatumtill,totalareal_enhet,totalareal_varde,vattenareal_enhet,vattenareal_varde,versiongiltigfran,versiongiltigtill
    -> AttributeManager_3
AttributeManager_3
    ATTR_TABLE = RENAME_SET_VALUE namnkortform > lan (buffer)
    -> SpatialFilter_2 [Filter]
    -> lan_namn (writer OGCGEOPACKAGE_2)
SpatialFilter_2
    AGGREGATE_HANDLING = Yes
    ATTR_CONFLICT_RES_LOOKUP = CANDIDATE_IF_CONFLICT
    BOOL_OP = OR
    BOUNDING_BOX = NO
    CURVE_BOUNDARY_RULE = ENDPOINTS_MOD2
    MULTI_BASE = YES
    PREDATTR = _predicate
    PREDICATES = INTERSECTS
    ATTR_ACCUM_MODE = Merge Filter
    ATTR_CONFLICT_RES = Use Candidate
    BASE_TYPE = Multiple Filters
    CURVE_BOUNDARY_RULE_PARAM = Default Rule
    PASS_CRITERIA = Pass Against One Filter
    USE_BOUNDING_BOX = No
    PASSED -> SpatialFilter_3 [Candidate]
lan_namn (writer OGCGEOPACKAGE_2)
    attributes: lan text
socknar_sverige (reader SHAPEFILE_1)
    attributes: SNID_1 varchar(16), SNID_2 varchar(16), SNID_3 varchar(16), SNID_4 number(16,0), NAMN varchar(254), LAN varchar(254), NOT varchar(50), KOMMENTAR varchar(254), DATUM varchar(16), VERSION varchar(16), KALLA varchar(25), AREA double, PERIMETER double, HECTARES double
    -> AttributeRemover_4
AttributeRemover_4
    REMOVE_ATTRS = AREA,DATUM,HECTARES,KALLA,KOMMENTAR,LAN,NOT,PERIMETER,SNID_1,SNID_2,SNID_3,SNID_4,VERSION
    -> AttributeManager_4
AttributeManager_4
    ATTR_TABLE = RENAME_SET_VALUE NAMN > socken (varchar(254))
    USER_EXPOSED_ATTRIBUTES = namnkortform
    -> SpatialFilter_3 [Filter]
    -> socken_namn (writer OGCGEOPACKAGE_2)
SpatialFilter_3
    AGGREGATE_HANDLING = Yes
    ATTR_CONFLICT_RES_LOOKUP = CANDIDATE_IF_CONFLICT
    BOOL_OP = OR
    BOUNDING_BOX = NO
    CURVE_BOUNDARY_RULE = ENDPOINTS_MOD2
    MULTI_BASE = YES
    PREDATTR = _predicate
    PREDICATES = INTERSECTS
    ATTR_ACCUM_MODE = Merge Filter
    ATTR_CONFLICT_RES = Use Candidate
    BASE_TYPE = Multiple Filters
    CURVE_BOUNDARY_RULE_PARAM = Default Rule
    PASS_CRITERIA = Pass Against One Filter
    USE_BOUNDING_BOX = No
    PASSED -> AttributeRemover
AttributeRemover
    REMOVE_ATTRS = Exploateringstyp,fid,Inventarienummer,Lst Dnr,pk,Plats,Projektkod,Projektledare,Projektnamn,Raä Dnr,SiteId,Slutdatum,Undersökningstyp,Uppdragsgivare
    -> AttributeManager_5
AttributeManager_5
    ATTR_TABLE:
      SET_TO rapport (varchar(200))
      SET_TO forfattare (varchar(200))
      SET_TO utgivnings_ar (varchar(200))
      SET_TO link_rapport (varchar(200))
      REMOVE _predicate (buffer)
    -> undersokningar_intrasis (writer OGCGEOPACKAGE_2)
undersokningar_intrasis (writer OGCGEOPACKAGE_2)
    attributes: gpkg_name text, uppdragsnummer text(9), beslutande_myndighet text(255), beslutsdatum date, diarienummer text(255), uppdragstyp text(255), utforande_organisation text(255), nollresultat text(9), url text(255), status text(255), lan text, kommun text, socken text, rapport text, forfattare text, utgivnings_ar text, link_rapport text
socken_namn (writer OGCGEOPACKAGE_2)
    attributes: socken text(254)

Bookmark: 1990 års uppdelning
kommun (reader OGCGEOPACKAGE_3)
    attributes: objektidentitet text, objektversion int, versiongiltigfran datetime, versiongiltigtill datetime, objekttyp text, enhetstyp text, gransstatus text, lanskod text, kommunkod text, landskod text, hogstaforvaltningsniva text, beslutatnamn text, namnkortform text, landareal_varde int, landareal_enhet text, vattenareal_varde int, vattenareal_enhet text, totalareal_varde int, totalareal_enhet text, referensdatumfran date, referensdatumtill date, id int,PrimaryKey
    -> AttributeRemover_2
lan (reader OGCGEOPACKAGE_3)
    attributes: objektidentitet text, objektversion int, versiongiltigfran datetime, versiongiltigtill datetime, objekttyp text, enhetstyp text, gransstatus text, lanskod text, lansbokstav text, landskod text, hogstaforvaltningsniva text, beslutatnamn text, namnkortform text, landareal_varde int, landareal_enhet text, vattenareal_varde int, vattenareal_enhet text, totalareal_varde int, totalareal_enhet text, referensdatumfran date, referensdatumtill date, id int,PrimaryKey
    -> AttributeRemover_3
rike (reader OGCGEOPACKAGE_3) [off]
    attributes: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

Bookmark: beslutande myndighet
arkeologiska_uppdrag_undersökningsområden_sverige_linestring (reader OGCGEOPACKAGE_4)
    attributes: id text(255), uppdragsnummer text(9), beslutande_myndighet text(255), beslutsdatum date, diarienummer text(255), uppdragstyp text(255), utforande_organisation text(255), nollresultat text(9), url text(255), status text(255), lan text, kommun text, socken text, fid int,PrimaryKey
    -> DuplicateFilter
arkeologiska_uppdrag_undersökningsområden_sverige_point (reader OGCGEOPACKAGE_4)
    attributes: id text(255), uppdragsnummer text(9), beslutande_myndighet text(255), beslutsdatum date, diarienummer text(255), uppdragstyp text(255), utforande_organisation text(255), nollresultat text(9), url text(255), status text(255), lan text, kommun text, socken text, fid int,PrimaryKey
    -> DuplicateFilter
arkeologiska_uppdrag_undersökningsområden_sverige_polygon (reader OGCGEOPACKAGE_4)
    attributes: id text(255), uppdragsnummer text(9), beslutande_myndighet text(255), beslutsdatum date, diarienummer text(255), uppdragstyp text(255), utforande_organisation text(255), nollresultat text(9), url text(255), status text(255), lan text, kommun text, socken text, fid int,PrimaryKey
    -> DuplicateFilter
DuplicateFilter
    INPUT_ORDERED_CHOICE_LOOKUP = NO
    KEYATTR = uppdragsnummer
    INPUT_ORDERED_CHOICE = No
    UNIQUE -> DuplicateFilter_4 [off]
    UNIQUE -> DuplicateFilter_3 [off]
    UNIQUE -> Tester_2
    UNIQUE -> DuplicateFilter_2 [off]
Tester_2 [off]
    BOOL_OP = OR
    TEST_CLAUSE:
      TEST @Value(diarienummer) = Okänt
      TEST diarienummer NOT_ATTRIBUTE_HAS_A_VALUE ""
    TEST_MODE = TEST
DuplicateFilter_3 [off]
    INPUT_ORDERED_CHOICE_LOOKUP = NO
    KEYATTR = beslutande_myndighet
    INPUT_ORDERED_CHOICE = No
    UNIQUE -> AttributeKeeper [off]
AttributeKeeper [off]
    CREATE_BULK_MODE_FEATURES = NO
    KEEP_ATTRS = beslutande_myndighet
    -> GeometryRemover [off]
GeometryRemover [off]
    REMOVE_COORDSYS = No
    -> beslutande_myndighet (writer OGCGEOPACKAGE_2) [off]
beslutande_myndighet (writer OGCGEOPACKAGE_2) [off]
    attributes: beslutande_myndighet text(255)
DuplicateFilter_2 [off]
    INPUT_ORDERED_CHOICE_LOOKUP = NO
    KEYATTR = uppdragstyp
    INPUT_ORDERED_CHOICE = No
    UNIQUE -> AttributeKeeper_2 [off]
AttributeKeeper_2 [off]
    CREATE_BULK_MODE_FEATURES = NO
    KEEP_ATTRS = uppdragstyp
    -> GeometryRemover_2 [off]
GeometryRemover_2 [off]
    REMOVE_COORDSYS = No
    -> uppdrags_typ (writer OGCGEOPACKAGE_2) [off]
uppdrags_typ (writer OGCGEOPACKAGE_2) [off]
    attributes: uppdragstyp text(255)
DuplicateFilter_4 [off]
    INPUT_ORDERED_CHOICE_LOOKUP = NO
    KEYATTR = utforande_organisation
    INPUT_ORDERED_CHOICE = No
