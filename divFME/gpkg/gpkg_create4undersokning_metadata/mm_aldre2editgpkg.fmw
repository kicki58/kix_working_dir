FME workspace mm_aldre2editgpkg.fmw

Parameters:
- DestDataset_OGCGEOPACKAGE = C:\ny_slask\mm_intrasis2ages\mm2ages_register_2.gpkg   # GeoPackage File
- SourceDataset_SHAPEFILE = C:\ny_slask\GIS-data\socknar_sverige\socken\socknar_sverige.shp   # Source Esri Shapefile(s)
- SourceDataset_OGCGEOPACKAGE_7 = C:\ny_slask\GIS-data\kommun-lan-rike_1990\kommun-lan-rike_1990.gpkg   # GeoPackage File
- SourceDataset_OGCGEOPACKAGE_2 = C:\ny_slask\GIS-data\arkeologiska_uppdrag_undersökningsområden_sverige (6).gpkg   # GeoPackage File
- SourceDataset_OGCGEOPACKAGE = C:\ny_slask\mm_intrasis2ages\oresunds_forbindelsen_data.gpkg   # GeoPackage File
- SourceDataset_OGCGEOPACKAGE_6 = C:\ny_slask\mm_intrasis2ages\ovrigt_data.gpkg   # GeoPackage File

Readers:
- SHAPEFILE_1: SHAPEFILE from $(SourceDataset_SHAPEFILE) in EPSG:3006
- OGCGEOPACKAGE_3: OGCGEOPACKAGE from $(SourceDataset_OGCGEOPACKAGE_7) in EPSG:3006
- OGCGEOPACKAGE_4: OGCGEOPACKAGE from $(SourceDataset_OGCGEOPACKAGE_2) in EPSG:3006
- OGCGEOPACKAGE_1: OGCGEOPACKAGE from $(SourceDataset_OGCGEOPACKAGE) in EPSG:3006
- OGCGEOPACKAGE_5: OGCGEOPACKAGE from $(SourceDataset_OGCGEOPACKAGE_6) in EPSG:3006

Writers:
- OGCGEOPACKAGE_2: OGCGEOPACKAGE to $(DestDataset_OGCGEOPACKAGE)

features (reader OGCGEOPACKAGE_1) [off]
    attributes: gpkg-name text, id int,PrimaryKey
    -> Aggregator
features (reader OGCGEOPACKAGE_5)
    attributes: gpkg-name text, id int,PrimaryKey
    -> Aggregator
Aggregator
    ACCUM_ATTRS = None
    AGGREGATE_TYPE = Homogeneous Collection (If Possible)
    GROUP_BY = gpkg-name
    MODE = Geometry - Assemble One Level
    SEP = ,
    AGGREGATE -> CenterPointExtractor
CenterPointExtractor
    CENTX = _inside_x
    CENTY = _inside_y
    CENTZ = _inside_z
    EXTRACTIONMODE = CENTEROFGRAV
    -> VertexCreator
VertexCreator
    MEASURE_TYPE_LOOKUP = CONTINUOUS
    MODE = REPLACE
    REMOVE_ATTRIBUTES = No
    XVAL = @Value(_inside_x)
    YVAL = @Value(_inside_y)
    MEASURE_TYPE = Continuous
    MODE_NAME = Replace with Point
    -> AttributeManager_6
AttributeManager_6
    ATTR_TABLE:
      RENAME_SET_VALUE gpkg-name > gpkg_name (buffer)
      SET_TO uppdragsnummer (varchar(6)) = saknas
      SET_TO beslutande_myndighet (varchar(200))
      SET_TO beslutsdatum (varchar(200))
      SET_TO diarienummer (buffer)
      SET_TO uppdragstyp (varchar(200))
      SET_TO utforande_organisation (varchar(12)) = Malmö museer
      SET_TO nollresultat (varchar(200))
      SET_TO url (varchar(6)) = saknas
      SET_TO status (varchar(200))
      REMOVE _inside_x (real64)
      REMOVE _inside_y (real64)
      REMOVE _inside_z (real64)
    USER_EXPOSED_ATTRIBUTES = path_rootname
    -> SpatialFilter [Candidate]
AttributeRemover_2
    REMOVE_ATTRS = beslutatnamn,enhetstyp,gransstatus,hogstaforvaltningsniva,id,kommunkod,landareal_enhet,landareal_varde,landskod,lanskod,objektidentitet,objekttyp,objektversion,referensdatumfran,referensdatumtill,totalareal_enhet,totalareal_varde,vattenareal_enhet,vattenareal_varde,versiongiltigfran,versiongiltigtill
    -> AttributeManager_2
AttributeManager_2
    ATTR_TABLE = RENAME_SET_VALUE namnkortform > kommun (buffer)
    -> SpatialFilter [Filter]
    -> kommun_namn (writer OGCGEOPACKAGE_2)
SpatialFilter
    AGGREGATE_HANDLING = Yes
    ATTR_CONFLICT_RES_LOOKUP = CANDIDATE_IF_CONFLICT
    BOOL_OP = OR
    BOUNDING_BOX = NO
    CURVE_BOUNDARY_RULE = ENDPOINTS_MOD2
    MULTI_BASE = YES
    PREDATTR = _predicate
    PREDICATES = INTERSECTS
    ATTR_ACCUM_MODE = Merge Filter
    ATTR_CONFLICT_RES = Use Candidate
    BASE_TYPE = Multiple Filters
    CURVE_BOUNDARY_RULE_PARAM = Default Rule
    PASS_CRITERIA = Pass Against One Filter
    USE_BOUNDING_BOX = No
    PASSED -> SpatialFilter_2 [Candidate]
kommun_namn (writer OGCGEOPACKAGE_2)
    attributes: kommun text
AttributeRemover_3
    REMOVE_ATTRS = beslutatnamn,enhetstyp,gransstatus,hogstaforvaltningsniva,id,landareal_enhet,landareal_varde,landskod,lansbokstav,lanskod,objektidentitet,objekttyp,objektversion,referensdatumfran,referensdatumtill,totalareal_enhet,totalareal_varde,vattenareal_enhet,vattenareal_varde,versiongiltigfran,versiongiltigtill
    -> AttributeManager_3
AttributeManager_3
    ATTR_TABLE = RENAME_SET_VALUE namnkortform > lan (buffer)
    -> SpatialFilter_2 [Filter]
    -> lan_namn (writer OGCGEOPACKAGE_2)
SpatialFilter_2
    AGGREGATE_HANDLING = Yes
    ATTR_CONFLICT_RES_LOOKUP = CANDIDATE_IF_CONFLICT
    BOOL_OP = OR
    BOUNDING_BOX = NO
    CURVE_BOUNDARY_RULE = ENDPOINTS_MOD2
    MULTI_BASE = YES
    PREDATTR = _predicate
    PREDICATES = INTERSECTS
    ATTR_ACCUM_MODE = Merge Filter
    ATTR_CONFLICT_RES = Use Candidate
    BASE_TYPE = Multiple Filters
    CURVE_BOUNDARY_RULE_PARAM = Default Rule
    PASS_CRITERIA = Pass Against One Filter
    USE_BOUNDING_BOX = No
    PASSED -> SpatialFilter_3 [Candidate]
lan_namn (writer OGCGEOPACKAGE_2)
    attributes: lan text
socknar_sverige (reader SHAPEFILE_1)
    attributes: SNID_1 varchar(16), SNID_2 varchar(16), SNID_3 varchar(16), SNID_4 number(16,0), NAMN varchar(254), LAN varchar(254), NOT varchar(50), KOMMENTAR varchar(254), DATUM varchar(16), VERSION varchar(16), KALLA varchar(25), AREA double, PERIMETER double, HECTARES double
    -> AttributeRemover_4
AttributeRemover_4
    REMOVE_ATTRS = AREA,DATUM,HECTARES,KALLA,KOMMENTAR,LAN,NOT,PERIMETER,SNID_1,SNID_2,SNID_3,SNID_4,VERSION
    -> AttributeManager_4
AttributeManager_4
    ATTR_TABLE = RENAME_SET_VALUE NAMN > socken (varchar(254))
    USER_EXPOSED_ATTRIBUTES = namnkortform
    -> SpatialFilter_3 [Filter]
    -> socken_namn (writer OGCGEOPACKAGE_2)
SpatialFilter_3
    AGGREGATE_HANDLING = Yes
    ATTR_CONFLICT_RES_LOOKUP = CANDIDATE_IF_CONFLICT
    BOOL_OP = OR
    BOUNDING_BOX = NO
    CURVE_BOUNDARY_RULE = ENDPOINTS_MOD2
    MULTI_BASE = YES
    PREDATTR = _predicate
    PREDICATES = INTERSECTS
    ATTR_ACCUM_MODE = Merge Filter
    ATTR_CONFLICT_RES = Use Candidate
    BASE_TYPE = Multiple Filters
    CURVE_BOUNDARY_RULE_PARAM = Default Rule
    PASS_CRITERIA = Pass Against One Filter
    USE_BOUNDING_BOX = No
    PASSED -> AttributeRemover
AttributeRemover
    REMOVE_ATTRS = Exploateringstyp,fid,Inventarienummer,Lst Dnr,pk,Plats,Projektkod,Projektledare,Projektnamn,Raä Dnr,SiteId,Slutdatum,Undersökningstyp,Uppdragsgivare
    -> AttributeManager_5
AttributeManager_5
    ATTR_TABLE:
      SET_TO rapport (varchar(200))
      SET_TO forfattare (varchar(200))
      SET_TO utgivnings_ar (varchar(200))
      SET_TO link_rapport (varchar(200))
      REMOVE _predicate (buffer)
    -> undersokningar_ovriga (writer OGCGEOPACKAGE_2)
undersokningar_ovriga (writer OGCGEOPACKAGE_2)
    attributes: gpkg_name text, uppdragsnummer text(9), beslutande_myndighet text(255), beslutsdatum date, diarienummer text(255), uppdragstyp text(255), utforande_organisation text(255), nollresultat text(9), url text(255), status text(255), lan text, kommun text, socken text, rapport text, forfattare text, utgivnings_ar text, link_rapport text
socken_namn (writer OGCGEOPACKAGE_2)
    attributes: socken text(254)

Bookmark: 1990 års uppdelning
kommun (reader OGCGEOPACKAGE_3) [off]
    attributes: objektidentitet text, objektversion int, versiongiltigfran datetime, versiongiltigtill datetime, objekttyp text, enhetstyp text, gransstatus text, lanskod text, kommunkod text, landskod text, hogstaforvaltningsniva text, beslutatnamn text, namnkortform text, landareal_varde int, landareal_enhet text, vattenareal_varde int, vattenareal_enhet text, totalareal_varde int, totalareal_enhet text, referensdatumfran date, referensdatumtill date, id int,PrimaryKey
    -> AttributeRemover_2
lan (reader OGCGEOPACKAGE_3) [off]
    attributes: objektidentitet text, objektversion int, versiongiltigfran datetime, versiongiltigtill datetime, objekttyp text, enhetstyp text, gransstatus text, lanskod text, lansbokstav text, landskod text, hogstaforvaltningsniva text, beslutatnamn text, namnkortform text, landareal_varde int, landareal_enhet text, vattenareal_varde int, vattenareal_enhet text, totalareal_varde int, totalareal_enhet text, referensdatumfran date, referensdatumtill date, id int,PrimaryKey
    -> AttributeRemover_3
rike (reader OGCGEOPACKAGE_3) [off]
    attributes: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

Bookmark: beslutande myndighet
arkeologiska_uppdrag_undersökningsområden_sverige_linestring (reader OGCGEOPACKAGE_4) [off]
    attributes: id text(255), uppdragsnummer text(9), beslutande_myndighet text(255), beslutsdatum date, diarienummer text(255), uppdragstyp text(255), utforande_organisation text(255), nollresultat text(9), url text(255), status text(255), lan text, kommun text, socken text, fid int,PrimaryKey
    -> DuplicateFilter [off]
arkeologiska_uppdrag_undersökningsområden_sverige_point (reader OGCGEOPACKAGE_4) [off]
    attributes: id text(255), uppdragsnummer text(9), beslutande_myndighet text(255), beslutsdatum date, diarienummer text(255), uppdragstyp text(255), utforande_organisation text(255), nollresultat text(9), url text(255), status text(255), lan text, kommun text, socken text, fid int,PrimaryKey
    -> DuplicateFilter [off]
arkeologiska_uppdrag_undersökningsområden_sverige_polygon (reader OGCGEOPACKAGE_4) [off]
    attributes: id text(255), uppdragsnummer text(9), beslutande_myndighet text(255), beslutsdatum date, diarienummer text(255), uppdragstyp text(255), utforande_organisation text(255), nollresultat text(9), url text(255), status text(255), lan text, kommun text, socken text, fid int,PrimaryKey
    -> DuplicateFilter [off]
DuplicateFilter [off]
    INPUT_ORDERED_CHOICE_LOOKUP = NO
    KEYATTR = uppdragsnummer
    INPUT_ORDERED_CHOICE = No
    UNIQUE -> DuplicateFilter_4 [off]
    UNIQUE -> DuplicateFilter_3 [off]
    UNIQUE -> Tester_2 [off]
    UNIQUE -> DuplicateFilter_2 [off]
Tester_2 [off]
    BOOL_OP = OR
    TEST_CLAUSE:
      TEST @Value(diarienummer) = Okänt
      TEST diarienummer NOT_ATTRIBUTE_HAS_A_VALUE ""
    TEST_MODE = TEST
DuplicateFilter_3 [off]
    INPUT_ORDERED_CHOICE_LOOKUP = NO
    KEYATTR = beslutande_myndighet
    INPUT_ORDERED_CHOICE = No
    UNIQUE -> AttributeKeeper [off]
AttributeKeeper [off]
    CREATE_BULK_MODE_FEATURES = NO
    KEEP_ATTRS = beslutande_myndighet
    -> GeometryRemover [off]
GeometryRemover [off]
    REMOVE_COORDSYS = No
    -> beslutande_myndighet (writer OGCGEOPACKAGE_2) [off]
beslutande_myndighet (writer OGCGEOPACKAGE_2) [off]
    attributes: beslutande_myndighet text(255)
DuplicateFilter_2 [off]
    INPUT_ORDERED_CHOICE_LOOKUP = NO
    KEYATTR = uppdragstyp
    INPUT_ORDERED_CHOICE = No
    UNIQUE -> AttributeKeeper_2 [off]
AttributeKeeper_2 [off]
    CREATE_BULK_MODE_FEATURES = NO
    KEEP_ATTRS = uppdragstyp
    -> GeometryRemover_2 [off]
GeometryRemover_2 [off]
    REMOVE_COORDSYS = No
    -> uppdrags_typ (writer OGCGEOPACKAGE_2) [off]
uppdrags_typ (writer OGCGEOPACKAGE_2) [off]
    attributes: uppdragstyp text(255)
DuplicateFilter_4 [off]
    INPUT_ORDERED_CHOICE_LOOKUP = NO
    KEYATTR = utforande_organisation
    INPUT_ORDERED_CHOICE = No
