FME workspace check_SRID_runner_from_excel.fmw

Parameters:
- SourceDataset_PATH = C:\ny_slask\mm_3\3 - Klar\3 - Klar   # INCLUDE_WEB_BROWSER Source Folder and File Pathnames Folder
- RECURSE_DIRECTORIES_PATH = NO   # Recurse Into Subfolders

Readers:
- PATH_1: PATH from $(SourceDataset_PATH)

PATH (reader PATH_1)
    attributes: path_unix buffer, path_windows buffer, path_rootname buffer, path_filename buffer, path_extension buffer, path_directory_unix buffer, path_directory_windows buffer, path_type char(10)
    -> Tester
Tester
    BOOL_OP = OR
    TEST_CLAUSE = CASE_INSENSITIVE_TEST @Value(path_rootname) NOT_BEGINS_WITH aggreg
    TEST_MODE = TEST
    PASSED -> AttributeManager
AttributeManager
    ATTR_TABLE = SET_TO excelfil (varchar(200)) = @Value(path_directory_windows)\srid.xlsx
    -> WorkspaceRunner
WorkspaceRunner
    BLOCKING = Yes
    WORKSPACE_FILE = $(FME_MF_DIR)wsr\check_SRID.fmw
    WORKSPACE_PARAMETERS = SourceDataset_SQLITE3,@Value(path_windows),gpkg_name,@Value(path_rootname),DestDataset_XLSXW,@Value(excelfil)
