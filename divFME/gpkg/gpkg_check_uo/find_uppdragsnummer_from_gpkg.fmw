FME workspace find_uppdragsnummer_from_gpkg.fmw

Parameters:
- SourceDataset_OGCGEOPACKAGE = C:\ny_slask\arkeologerna\aggregated_reprojected.gpkg   # GeoPackage File
- SourceDataset_OGCGEOPACKAGE_5 = C:\ny_slask\GIS-data\arkeologiska_uppdrag_undersökningsområden_sverige (6).gpkg   # GeoPackage File
- DestDataset_OGCGEOPACKAGE = C:\ny_slask\arkeologerna\jmfr4.gpkg   # GeoPackage File

Readers:
- OGCGEOPACKAGE_1: OGCGEOPACKAGE from $(SourceDataset_OGCGEOPACKAGE)
- OGCGEOPACKAGE_2: OGCGEOPACKAGE from $(SourceDataset_OGCGEOPACKAGE_5) in EPSG:3006

Writers:
- OGCGEOPACKAGE_4: OGCGEOPACKAGE to $(DestDataset_OGCGEOPACKAGE)

features_line (reader OGCGEOPACKAGE_1)
    attributes: intrasis_name text, object_id mediumint, class text, subclass text, symbolid mediumint, geoobjectid mediumint, spatial_type text, id int,PrimaryKey
    -> Bufferer_2
features_point (reader OGCGEOPACKAGE_1)
    attributes: intrasis_name text, object_id mediumint, class text, subclass text, symbolid mediumint, geoobjectid mediumint, spatial_type text, id int,PrimaryKey
    -> Bufferer_2
Bufferer_2
    ANGLE = 22.5
    CAP_STYLE_LOOKUP = CAP_ARC
    CORNER_STYLE_LOOKUP = JOIN_ARC
    MODE = AREA
    OFFSET = 50
    OFFSET_UNITS = NONE
    PRECISION = APPROX
    CAP_STYLE = Arc
    CORNER_STYLE = Arc
    BUFFERED -> Aggregator_3
features_polygon (reader OGCGEOPACKAGE_1)
    attributes: intrasis_name text, object_id mediumint, class text, subclass text, symbolid mediumint, geoobjectid mediumint, spatial_type text, id int,PrimaryKey
    -> Aggregator_3
project_information (reader OGCGEOPACKAGE_1)
    attributes: intrasis_name text, pk mediumint, siteid text, plats text, lst dnr text, raä dnr text, inventarienummer text, projektkod text, projektnamn text, projektledare text, uppdragsgivare text, exploateringstyp text, undersökningstyp text, slutdatum text, beskrivning text, id int,PrimaryKey
    -> Aggregator_3
Aggregator_3
    ACCUM_ATTRS = One
    AGGREGATE_TYPE = Homogeneous Collection (If Possible)
    GROUP_BY = intrasis_name
    MODE = Geometry - Assemble One Level
    SEP = ,
    AGGREGATE -> SpatialRelator [Requestor]
SpatialRelator
    AGGREGATE_HANDLING = Yes
    CALC_CARD = No
    CURVE_BOUNDARY_RULE_PARAM = Default Rule
    LIST_ATTRS_TO_INCLUDE = diarienummer uppdragsnummer url
    LIST_NAME = _relationships
    PREDICATES = INTERSECTS WITHIN CONTAINS EQUALS TOUCHES
    SUCCESS_ATTR = _related_suppliers
    -> Tester_2
Tester_2
    BOOL_OP = OR
    TEST_CLAUSE = TEST @Value(_related_suppliers) > 0
    TEST_MODE = TEST
    PASSED -> FeatureMerger [REQUESTOR]
    FAILED -> FeatureMerger [REQUESTOR]
FeatureMerger
    ATTR_ACCUM_MODE = Merge Supplier
    ATTR_CONFLICT_RES_LOOKUP = REQUESTOR_IF_CONFLICT
    IGNORE_NULLS = No
    JOIN_KEYS = @Value(intrasis_name) @Value(arkeologenrna_path_rootname) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> ListConcatenator_5
ListConcatenator_5
    DROP_EMPTY_PARTS = No
    LIST_ATTR = _relationships{}.uppdragsnummer
    SEP = "  ,  "
    VAL_ATTR = _upp
    -> ListConcatenator_6
ListConcatenator_6
    DROP_EMPTY_PARTS = No
    LIST_ATTR = _relationships{}.url
    SEP = "   ,   "
    VAL_ATTR = _url
    -> ListSearcher
ListSearcher
    ATTR_VALUE = @Value(arkeologenrna_uppdragsnummer)
    CASE = CASE_SENSITIVE
    INDEX_ATTR = _list_index
    LIST_ATTR = _relationships{}.uppdragsnummer
    MATCHTYPE = FIRST_MATCHED_ENCODED
    FOUND -> AttributeManager_5
AttributeManager_5
    ATTR_TABLE = SET_TO from_arkelogerna (varchar(11)) = uppdrags_nr
    -> AttributeManager
AttributeManager
    ATTR_TABLE:
      SET_TO hittad_uo (varchar(200)) = @Value(_relationships{@Value(_list_index)}.uppdragsnummer)
      SET_TO hittad_url (varchar(200)) = @Value(_relationships{@Value(_list_index)}.url)
      SET_TO verifierad (varchar(200))
      REMOVE id (int64)
      REMOVE fid (int64)
    -> Deaggregator_2
    -> kollade_mot_uo (writer OGCGEOPACKAGE_4)
Deaggregator_2
    ATTR_ACCUM_MODE = HANDLE_CONFLICT
    ATTR_CONFLICT_RES = INCOMING_IF_CONFLICT
    EXPLODE_INSTANCES = No
    GEOM_LABEL_FIELD = _geometry_label
    LIST_ATTR_MODE_LOOKUP = LEAN
    PART_NUMBER_FIELD = _part_number
    RECURSIVE = No
    SPLIT_COMPOSITES = No
    DEAGGREGATED -> kollade_mot_uo_deagg (writer OGCGEOPACKAGE_4)
kollade_mot_uo_deagg (writer OGCGEOPACKAGE_4)
    attributes: intrasis_name text, hittad_uo text(200), hittad_url text(200), pk mediumint, siteid text, plats text, lst dnr text, raä dnr text, inventarienummer text, projektkod text, projektnamn text, projektledare text, uppdragsgivare text, exploateringstyp text, undersökningstyp text, slutdatum text, beskrivning text, object_id mediumint, class text, subclass text, symbolid mediumint, geoobjectid mediumint, spatial_type text, _relationships{}.uppdragsnummer text(9), _relationships{}.diarienummer text(255), _relationships{}.url text(255), _relationships{}.de9im text, _relationships{}.pass{} text, _related_suppliers int, arkeologenrna_path_unix text,
      arkeologenrna_path_windows text, arkeologenrna_path_rootname text, arkeologenrna_path_filename text, arkeologenrna_path_extension text, arkeologenrna_path_directory_unix text, arkeologenrna_path_directory_windows text, arkeologenrna_path_type text(10), arkeologenrna_uppdragsnummer text, arkeologenrna_u-nummer text, arkeologenrna_lst dnr text, _list_index int, uppdragsnummer text(9), beslutande_myndighet text(255), beslutsdatum date, diarienummer text(255), uppdragstyp text(255), utforande_organisation text(255), nollresultat text(9), url text(255), status text(255), lan text, kommun text, socken text, _upp text, _url text, _part_number text(20), _geometry_label text
kollade_mot_uo (writer OGCGEOPACKAGE_4)
    attributes: intrasis_name text, hittad_uo text(200), hittad_url text(200), verifierad text(200), _upp text, _url text, from_arkelogerna text(16), pk mediumint, siteid text, plats text, lst dnr text, raä dnr text, inventarienummer text, projektkod text, projektnamn text, projektledare text, uppdragsgivare text, exploateringstyp text, undersökningstyp text, slutdatum text, beskrivning text, object_id mediumint, class text, subclass text, symbolid mediumint, geoobjectid mediumint, spatial_type text, _relationships{}.uppdragsnummer text(9), _relationships{}.diarienummer text(255), _relationships{}.url text(255),
      _relationships{}.de9im text, _relationships{}.pass{} text, _related_suppliers int, arkeologenrna_path_unix text, arkeologenrna_path_windows text, arkeologenrna_path_rootname text, arkeologenrna_path_filename text, arkeologenrna_path_extension text, arkeologenrna_path_directory_unix text, arkeologenrna_path_directory_windows text, arkeologenrna_path_type text(10), arkeologenrna_uppdragsnummer text, arkeologenrna_u-nummer text, arkeologenrna_lst dnr text, _list_index int, uppdragsnummer text(9), beslutande_myndighet text(255), beslutsdatum date, diarienummer text(255), uppdragstyp text(255), utforande_organisation text(255), nollresultat text(9), url text(255), status text(255), lan text, kommun text, socken text
AttributeManager_2
    ATTR_TABLE:
      SET_TO hittad_uo (varchar(200))
      REMOVE fid (int64)
      REMOVE _relationships{}.uppdragsnummer (varchar(9))
      REMOVE _relationships{}.url (varchar(255))
      REMOVE _relationships{}.de9im (buffer)
      REMOVE _relationships{}.pass{} (buffer)
      REMOVE _related_suppliers (uint32)
      REMOVE id (int64)
    -> att_kolla_upp (writer OGCGEOPACKAGE_4)
    -> Deaggregator
Deaggregator
    ATTR_ACCUM_MODE = HANDLE_CONFLICT
    ATTR_CONFLICT_RES = INCOMING_IF_CONFLICT
    EXPLODE_INSTANCES = No
    GEOM_LABEL_FIELD = _geometry_label
    LIST_ATTR_MODE_LOOKUP = LEAN
    PART_NUMBER_FIELD = _part_number
    RECURSIVE = No
    SPLIT_COMPOSITES = No
    DEAGGREGATED -> att_kolla_upp_deagg (writer OGCGEOPACKAGE_4)
att_kolla_upp_deagg (writer OGCGEOPACKAGE_4)
    attributes: intrasis_name text, hittad_uo text(200), _upp text, _url text, pk mediumint, siteid text, plats text, lst dnr text, raä dnr text, inventarienummer text, projektkod text, projektnamn text, projektledare text, uppdragsgivare text, exploateringstyp text, undersökningstyp text, slutdatum text, beskrivning text, object_id mediumint, class text, subclass text, symbolid mediumint, geoobjectid mediumint, spatial_type text, _relationships{}.diarienummer text(255), arkeologenrna_path_unix text, arkeologenrna_path_windows text, arkeologenrna_path_rootname text, arkeologenrna_path_filename text, arkeologenrna_path_extension text,
      arkeologenrna_path_directory_unix text, arkeologenrna_path_directory_windows text, arkeologenrna_path_type text(10), arkeologenrna_uppdragsnummer text, arkeologenrna_u-nummer text, arkeologenrna_lst dnr text, uppdragsnummer text(9), beslutande_myndighet text(255), beslutsdatum date, diarienummer text(255), uppdragstyp text(255), utforande_organisation text(255), nollresultat text(9), url text(255), status text(255), lan text, kommun text, socken text, _part_number text(20), _geometry_label text
att_kolla_upp (writer OGCGEOPACKAGE_4)
    attributes: intrasis_name text, hittad_uo text(200), _upp text, _url text, pk mediumint, siteid text, plats text, lst dnr text, raä dnr text, inventarienummer text, projektkod text, projektnamn text, projektledare text, uppdragsgivare text, exploateringstyp text, undersökningstyp text, slutdatum text, beskrivning text, object_id mediumint, class text, subclass text, symbolid mediumint, geoobjectid mediumint, spatial_type text, _relationships{}.diarienummer text(255), arkeologenrna_path_unix text, arkeologenrna_path_windows text, arkeologenrna_path_rootname text, arkeologenrna_path_filename text, arkeologenrna_path_extension text,
      arkeologenrna_path_directory_unix text, arkeologenrna_path_directory_windows text, arkeologenrna_path_type text(10), arkeologenrna_uppdragsnummer text, arkeologenrna_u-nummer text, arkeologenrna_lst dnr text, uppdragsnummer text(9), beslutande_myndighet text(255), beslutsdatum date, diarienummer text(255), uppdragstyp text(255), utforande_organisation text(255), nollresultat text(9), url text(255), status text(255), lan text, kommun text, socken text
dubletter_lst_nr_5st (writer OGCGEOPACKAGE_4)
    attributes: uppdragsnummer text(9), diarienummer text(255), dublett_diarienummer text(255), arkeologenrna_lst dnr text, dublett_arkeologenrna_path_rootname text, dublett_arkeologenrna_lst dnr text, arkeologenrna_path_rootname text, dublett_url text(255), url text(255)

Bookmark: New Bookmark
arkeologiska_uppdrag_undersökningsområden_sverige_linestring (reader OGCGEOPACKAGE_2)
    attributes: id text(255), uppdragsnummer text(9), beslutande_myndighet text(255), beslutsdatum date, diarienummer text(255), uppdragstyp text(255), utforande_organisation text(255), nollresultat text(9), url text(255), status text(255), lan text, kommun text, socken text, fid int,PrimaryKey
    -> Bufferer
arkeologiska_uppdrag_undersökningsområden_sverige_point (reader OGCGEOPACKAGE_2)
    attributes: id text(255), uppdragsnummer text(9), beslutande_myndighet text(255), beslutsdatum date, diarienummer text(255), uppdragstyp text(255), utforande_organisation text(255), nollresultat text(9), url text(255), status text(255), lan text, kommun text, socken text, fid int,PrimaryKey
    -> Bufferer
Bufferer
    ANGLE = 22.5
    CAP_STYLE_LOOKUP = CAP_ARC
    CORNER_STYLE_LOOKUP = JOIN_ARC
    MODE = AREA
    OFFSET = 50
    OFFSET_UNITS = NONE
    PRECISION = APPROX
    CAP_STYLE = Arc
    CORNER_STYLE = Arc
    BUFFERED -> Aggregator
arkeologiska_uppdrag_undersökningsområden_sverige_polygon (reader OGCGEOPACKAGE_2)
    attributes: id text(255), uppdragsnummer text(9), beslutande_myndighet text(255), beslutsdatum date, diarienummer text(255), uppdragstyp text(255), utforande_organisation text(255), nollresultat text(9), url text(255), status text(255), lan text, kommun text, socken text, fid int,PrimaryKey
    -> Aggregator
Aggregator
    ACCUM_ATTRS = One
    AGGREGATE_TYPE = Homogeneous Collection (If Possible)
    GROUP_BY = uppdragsnummer
    MODE = Geometry - Assemble One Level
    SEP = ,
    AGGREGATE -> Tester_4
Tester_4
    BOOL_OP = OR
    TEST_CLAUSE = TEST @Value(utforande_organisation) = STATENS HISTORISKA MUSEER
    TEST_MODE = TEST
    PASSED -> SpatialRelator [Supplier]
