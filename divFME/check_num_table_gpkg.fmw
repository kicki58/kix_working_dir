FME workspace check_num_table_gpkg.fmw

Parameters:
- SourceDataset_CSV2 = C:\Users\krima354\Work Folders\Documents\GitHub\kix_working_dir\urdar\db_on_urdar.csv   # Source CSV (Comma Separated Value) File(s)
- DestDataset_XLSXW = C:\Users\krima354\Work Folders\Documents\kicki_arbetsfiler\slask\test_gpkg\antal_tabeller_gpkg3.xlsx   # Destination Microsoft Excel File
- PATH_gpkg = C:\Users\krima354\Work Folders\Documents\kicki_arbetsfiler\slask\utdar230630\klara3006   # path to gpkg

Readers:
- CSV2_1: CSV2 from $(SourceDataset_CSV2)

Writers:
- XLSXW_1: XLSXW to $(DestDataset_XLSXW)

CSV (reader CSV2_1)
    attributes: intrasisarchive varchar(17)
    -> AttributeManager
AttributeManager
    ATTR_TABLE = SET_TO gpkg-file = $(PATH_gpkg)\@Value(intrasisarchive).gpkg
    USER_EXPOSED_ATTRIBUTES = gpkg-file
    -> FileExistenceChecker
FileExistenceChecker
    Input = @Value(gpkg-file)
    Exists -> SQLExecutor_3 [INITIATOR]
SQLExecutor_3
    ATTR_IGNORE_NULLS = Yes
    COMBINE_ATTRS = Keep Initiator Attributes if Conflict
    COMBINE_GEOM = Initiator Geometry Only
    DATASET = @Value(gpkg-file)
    EXPOSED_ATTRIBUTE_LIST = num_tables
    FORMAT = OGCGEOPACKAGE
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = NO
    OGCGEOPACKAGE_READ_BOOLEANS_AS_YES_NO = YES
    OGCGEOPACKAGE_READ_NULLS = YES
    OUTPUT_FEATURES_DISPLAY = Data Features
    SQL_STATEMENT = SELECT count(name) as num_tables FROM sqlite_schema WHERE type='table';
    RESULT -> SQLExecutor [INITIATOR]
SQLExecutor
    ATTR_IGNORE_NULLS = Yes
    COMBINE_ATTRS = Keep Initiator Attributes if Conflict
    COMBINE_GEOM = Initiator Geometry Only
    DATASET = @Value(gpkg-file)
    EXPOSED_ATTRIBUTE_LIST = Beskrivning,Exploateringstyp,fid,Inventarienummer,"Lst Dnr",pk,Plats,Projektkod,Projektledare,Projektnamn,"Raä Dnr",SiteId,Slutdatum,Undersökningstyp,Uppdragsgivare
    FORMAT = OGCGEOPACKAGE
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = NO
    OGCGEOPACKAGE_READ_BOOLEANS_AS_YES_NO = YES
    OGCGEOPACKAGE_READ_NULLS = YES
    OUTPUT_FEATURES_DISPLAY = Data Features
    SQL_STATEMENT = select * from project_information
    RESULT -> AttributeManager_3
    <REJECTED> -> AttributeManager_4
AttributeManager_3
    ATTR_TABLE = REMOVE _path
    -> med_proj_info (writer XLSXW_1)
med_proj_info (writer XLSXW_1)
    attributes: intrasisarchive string(17), num_tables string(20), gpkg-file string(200), Beskrivning string(20), Exploateringstyp string(20), fid string(20), Inventarienummer string(20), Lst Dnr string(20), pk string(20), Plats string(20), Projektkod string(20), Projektledare string(20), Projektnamn string(20), Raä Dnr string(20), SiteId string(20), Slutdatum string(20), Undersökningstyp string(20), Uppdragsgivare string(20)
AttributeManager_4
    ATTR_TABLE = REMOVE _path
    -> utan_proj_info (writer XLSXW_1)
utan_proj_info (writer XLSXW_1)
    attributes: intrasisarchive string(17), num_tables string(20), gpkg-file string(200), Beskrivning string(20), Exploateringstyp string(20), fid string(20), Inventarienummer string(20), Lst Dnr string(20), pk string(20), Plats string(20), Projektkod string(20), Projektledare string(20), Projektnamn string(20), Raä Dnr string(20), SiteId string(20), Slutdatum string(20), Undersökningstyp string(20), Uppdragsgivare string(20), _reader_error string(20)
Creator
    GEOMTYPE = Geometry Object
    NUM = 1
    CREATED -> AttributeManager_2
AttributeManager_2
    ATTR_TABLE = SET_TO gpkg-file = C:\Users\krima354\Work Folders\Documents\kicki_arbetsfiler\slask\utdar230630\klara3006\o2009125.gpkg
    USER_EXPOSED_ATTRIBUTES = gpkg-file
    -> FileExistenceChecker_2
FileExistenceChecker_2
    Input = @Value(gpkg-file)

FME custom transformer FileExistenceChecker
Description
This transformer checks if input file paths exist and routes features accordingly.
The transformer supports UNC path, Zip files(*.zip) and wildcards. 
Details
The transformer will check if the filename selected in InputPort exists or not. 
The path can be supplied from a parameter, a network share location, by selecting a filename or using wildcards. 
Notes
Multiple filenames are not supported
Path to file must exist (no missing folders in the path)
FTP paths are not supported
Input
Filename path to check if file exists.   
Parameters
Input ports
Input File Path: Full path to the file to check for existence.  
Output Ports
Exists:Features are output through this port if the file exists.   
_path: The attribute stores the path to the file.  
DoesNotExist:Features are output through this port if the file does not exists.   
_path: This attribute stores the path to the file.

Parameters:
- Input =   # Input File Path

Input (input)
    -> ParameterFetcher
ParameterFetcher
    ATTR_LIST = FEC_FullPath {$(Input)}
    -> PythonCaller
AttributeManager
    ATTR_TABLE = REMOVE FEC_exists
    -> Exists (output)
Exists (output)
AttributeManager_2
    ATTR_TABLE = REMOVE FEC_exists
    -> DoesNotExist (output)
DoesNotExist (output)

Bookmark: Check if File Exists
PythonCaller
    NEW_ATTRIBUTES = FEC_exists
    PYTHONSOURCE:
      import fmeobjects
      import glob
      import zipfile

      def processFeature(feature):

          # Get input path attribute
          fullpath=feature.getAttribute("FEC_FullPath")

          # Check if the file exists
          if glob.glob(fullpath):
              feature.setAttribute("FEC_exists","Yes")
              # if not, try checking inside a zip file
          else:
              fullpath = fullpath.replace("\\","/")
              idx = fullpath.find(".zip")
              if idx > -1:
                  zipPath = fullpath[:idx+4]
                  pathInZip = fullpath[idx+5:]    #i.e. .zip/
                  try:
                      with zipfile.ZipFile(zipPath, 'r') as f:
                          if isinstance(f.getinfo(pathInZip),zipfile.ZipInfo):
                              feature.setAttribute("FEC_exists","Yes")
                              return
                  except (KeyError, FileNotFoundError) as e:
                      pass
                  # not found in a zipfile or in filesystem - does not exist
                  feature.setAttribute("FEC_exists","No")
    PYTHONSYMBOL = processFeature
    -> AttributeRenamer
AttributeRenamer
    ATTR_TABLE = RENAME_SET_DEFAULT FEC_FullPath > _path
    MISSING_INPUT_ATTRS = PRESERVE
    -> Tester
Tester
    BOOL_OP = OR
    TEST_CLAUSE = TEST @Value(FEC_exists) = Yes
    TEST_MODE = TEST
    PASSED -> AttributeManager
    FAILED -> AttributeManager_2
