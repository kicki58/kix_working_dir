FME workspace create_importfile.fmw
Title: SAUimportIntrasis
Description: En import av SAU's databaser.
Vad som krävs
C:\Intrasis\backup_files
Backupfiler med vissa namn ändrade (de som har _ innan datumet i slutet)
pgpass.conf - med lösen för den dbhanteraren som man går mot
i katalogen C:\Users\krima354\AppData\Roaming\postgresql

Parameters:
- SourceDataset_PATH = C:\ny_slask\norrbottensmuseum\Intrasisprojekt\Backup   # INCLUDE_WEB_BROWSER Source Folder and File Pathnames Folder
- num2remove = 15   # numChar2remove
- SourceDataset_XLSXR = C:\ny_slask\norrbottensmuseum\Bilaga avtal om geodata_ifylld med samtlig info.xlsx   # Source Microsoft Excel File(s)
- DestDataset_XLSXW = C:\ny_slask\norrbottensmuseum\restorefile.xlsx   # Destination Microsoft Excel File

Readers:
- PATH_1: PATH from $(SourceDataset_PATH)
- XLSXR_1: XLSXR from $(SourceDataset_XLSXR)

Writers:
- XLSXW_1: XLSXW to $(DestDataset_XLSXW)

PATH (reader PATH_1)
    attributes: path_unix buffer, path_windows buffer, path_rootname buffer, path_filename buffer, path_extension buffer, path_directory_unix buffer, path_directory_windows buffer, path_type char(10)
    -> AttributeManager_2
AttributeManager_2
    ATTR_TABLE:
      REMOVE path_unix
      REMOVE path_windows
      REMOVE path_filename
      REMOVE path_extension
      REMOVE path_directory_unix
      REMOVE path_directory_windows
      REMOVE path_type
      SET_TO db_name = @LowerCase(@Left(@Value(path_rootname),@StringLength(@Value(path_rootname))-$(num2remove)))
    -> FeatureMerger [REQUESTOR]
Sheet1 (reader XLSXR_1)
    attributes: Nbm projektnamn char(52), Filnamn databas char(49), Nbm dnr char(18), Lst dnr char(45), Uppdragsnummer (i förekommande fall) char(11), Rapport (författare, årtal, titel) char(437), Rapport filnamn (om de skickas som PDF) char(233), Länk till rapport (i förekommande fall) char(74), Sekretess char(3)
    -> AttributeManager_3
AttributeManager_3
    ATTR_TABLE:
      SET_TO db_name = @LowerCase(@Left(@Value(Filnamn databas),@StringLength(@Value(Filnamn databas))-11))
      REMOVE Nbm projektnamn
      REMOVE Filnamn databas
      REMOVE Nbm dnr
      REMOVE Lst dnr
      REMOVE Rapport (författare, årtal, titel)
      REMOVE Länk till rapport (i förekommande fall)
      REMOVE Sekretess
    -> FeatureMerger [SUPPLIER]
FeatureMerger
    ATTR_ACCUM_MODE = Merge Supplier
    ATTR_CONFLICT_RES_LOOKUP = REQUESTOR_IF_CONFLICT
    IGNORE_NULLS = No
    JOIN_KEYS = @Value(db_name) @Value(db_name) AUTO
    MERGE_TYPE = Attributes Only
    PROCESS_DUPS = NO
    REJECT_NULL_MISSING_KEYS = No
    SUPPLIERS_FIRST = No
    ATTR_CONFLICT_RES = Use Requestor
    MERGED -> merged (writer XLSXW_1)
    UNMERGED_REQUESTOR -> unmergedReq (writer XLSXW_1)
    UNUSED_SUPPLIER -> unused_supplier (writer XLSXW_1)
merged (writer XLSXW_1)
    attributes: path_rootname string(20), db_name string(200), Uppdragsnummer (i förekommande fall) string(11), Rapport filnamn (om de skickas som PDF) string(233)
unmergedReq (writer XLSXW_1)
    attributes: path_rootname string(20), db_name string(200)
unused_supplier (writer XLSXW_1)
    attributes: db_name string(200), Uppdragsnummer (i förekommande fall) string(11), Rapport filnamn (om de skickas som PDF) string(233)
