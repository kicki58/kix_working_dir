FME workspace jmfr_filer_i_olika_mappar.fmw

Parameters:
- SourceDataset_PATH = C:\Program Files\FME\2026_1\Reproject\Gtrans\Sys   # INCLUDE_WEB_BROWSER Source Folder and File Pathnames Folder 1
- RECURSE_DIRECTORIES_PATH = YES   # Recurse Into Subfolders 1
- GLOB_PATTERN_PATH =   # Path Filter 1
- SourceDataset_PATH_3 = $(FME_HOME)Reproject\Gtrans\Sys   # INCLUDE_WEB_BROWSER Source Folder and File Pathnames Folder
- RECURSE_DIRECTORIES_PATH_2 = YES   # Recurse Into Subfolders 2
- GLOB_PATTERN_PATH_2 =   # Path Filter 2

Readers:
- PATH_1: PATH from $(SourceDataset_PATH)
- PATH_2: PATH from $(SourceDataset_PATH_3)

PATH (reader PATH_1)
    attributes: path_unix buffer, path_windows buffer, path_rootname buffer, path_filename buffer, path_extension buffer, path_directory_unix buffer, path_directory_windows buffer, path_type char(10)
    -> FeatureMerger [REQUESTOR]
PATH (reader PATH_2)
    attributes: path_unix buffer, path_windows buffer, path_rootname buffer, path_filename buffer, path_extension buffer, path_directory_unix buffer, path_directory_windows buffer, path_type char(10)
    -> FeatureMerger [SUPPLIER]
FeatureMerger
    ATTR_ACCUM_MODE = Merge Supplier
    ATTR_CONFLICT_RES_LOOKUP = REQUESTOR_IF_CONFLICT
    IGNORE_NULLS = No
    JOIN_KEYS = @Value(path_filename) @Value(path_filename) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
