FME workspace restoreDBfromBackupPath.fmw
Title: SAUimportIntrasis
Description: En import av SAU's databaser.
Vad som krävs
C:\Intrasis\backup_files
Backupfiler med vissa namn ändrade (de som har _ innan datumet i slutet)
pgpass.conf - med lösen för den dbhanteraren som man går mot
i katalogen C:\Users\krima354\AppData\Roaming\postgresql

Parameters:
- server = localhost   # Server
- port = 5432   # Port
- user = postgres   # User
- SourceDataset_CSV2 = C:\Users\krima354\Work Folders\Documents\kicki_arbetsfiler\slask\no_project_info.csv   # Source CSV (Comma Separated Value) File(s)
- SourceDataset_PATH_3 = C:\Users\krima354\Box\Urdar\DBackup   # INCLUDE_WEB_BROWSER Source Folder and File Pathnames Folder
- SourceDataset_CSV2_3 = C:\Users\krima354\Work Folders\Documents\kicki_arbetsfiler\slask\yunyun_georef.csv   # Source CSV (Comma Separated Value) File(s)

Readers:
- CSV2_1: CSV2 from $(SourceDataset_CSV2)
- PATH_2: PATH from $(SourceDataset_PATH_3)
- CSV2_2: CSV2 from $(SourceDataset_CSV2_3)

CSV (reader CSV2_2)
    attributes: databas varchar(10)
    -> FeatureMerger [REQUESTOR]
CSV (reader CSV2_1)
    attributes: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
PATH (reader PATH_2)
    attributes: path_unix buffer, path_windows buffer, path_rootname buffer, path_filename buffer, path_extension buffer, path_directory_unix buffer, path_directory_windows buffer, path_type char(10)
    -> AttributeManager_4
AttributeManager_4
    ATTR_TABLE = SET_TO path_rootname = @LowerCase(@Value(path_rootname))
    -> FeatureMerger [SUPPLIER]
FeatureMerger
    ATTR_ACCUM_MODE = Merge Supplier
    ATTR_CONFLICT_RES_LOOKUP = REQUESTOR_IF_CONFLICT
    IGNORE_NULLS = No
    JOIN_KEYS = @Value(databas) @Value(path_rootname) AUTO
    MERGE_TYPE = Attributes Only
    PRESERVE_FEATURE_ORDER_LOOKUP = PER_OUTPUT_PORT
    PROCESS_DUPS = NO
    REJECT_NULL_MISSING_KEYS = No
    SUPPLIERS_FIRST = No
    ATTR_CONFLICT_RES = Use Requestor
    MERGED -> AttributeManager
AttributeManager
    ATTR_TABLE:
      SET_TO restore = ""C:/Program Files/PostgreSQL/11/bin/pg_restore.exe" -h $(server)  -p $(port) -U $(user)  -w -d  @Value(databas) -O -x -c --no-security-labels "@Value(path_windows)""
      SET_TO createdb = ""C:/Program Files/PostgreSQL/11/bin/psql.exe" -h $(server)  -p $(port) -U $(user) -c "CREATE DATABASE  @Value(databas) WITH TEMPLATE = urdar_template ENCODING = 'UTF8'"
    -> SystemCaller_3
SystemCaller_3
    CMD = ""C:/Program Files/PostgreSQL/11/bin/psql.exe" -h $(server)  -p $(port) -U $(user) -c "CREATE DATABASE  @Value(databas) WITH TEMPLATE = urdar_template ENCODING = 'UTF8'"
    -> SystemCaller
SystemCaller
    ATTR = hejda
    CMD = ""C:/Program Files/PostgreSQL/11/bin/pg_restore.exe" -h $(server)  -p $(port) -U $(user)  -w -d @Value(databas) -O -x -c --no-security-labels "@Value(path_windows)""
