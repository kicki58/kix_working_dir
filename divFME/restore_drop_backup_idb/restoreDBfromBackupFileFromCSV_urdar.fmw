FME workspace restoreDBfromBackupFileFromCSV_urdar.fmw
Title: SAUimportIntrasis
Description: En import av SAU's databaser.
Vad som krävs
C:\Intrasis\backup_files
Backupfiler med vissa namn ändrade (de som har _ innan datumet i slutet)
pgpass.conf - med lösen för den dbhanteraren som man går mot
i katalogen C:\Users\krima354\AppData\Roaming\postgresql

Parameters:
- server = localhost   # Server
- port = 5432   # Port
- user = postgres   # User
- SourceDataset_CSV2 = C:\Users\krima354\Work Folders\Documents\kicki_arbetsfiler\slask\no_project_info.csv   # Source CSV (Comma Separated Value) File(s)
- SourceDataset_PATH_3 = C:\Users\krima354\Box\Urdar\DBackup   # INCLUDE_WEB_BROWSER Source Folder and File Pathnames Folder

Readers:
- CSV2_1: CSV2 from $(SourceDataset_CSV2)
- PATH_2: PATH from $(SourceDataset_PATH_3)

PATH (reader PATH_2)
    attributes: path_unix buffer, path_windows buffer, path_rootname buffer, path_filename buffer, path_extension buffer, path_directory_unix buffer, path_directory_windows buffer, path_type char(10)
    -> AttributeManager_4
AttributeManager_4
    ATTR_TABLE = SET_TO path_rootname = @LowerCase(@Value(path_rootname))
    -> FeatureMerger [SUPPLIER]
CSV (reader CSV2_1)
    attributes: databas varchar(10), num_tables uint32, gpkg-file varchar(102), Beskrivning varchar(1), Exploateringstyp varchar(1), fid varchar(1), Inventarienummer varchar(1), Lst Dnr varchar(1), pk varchar(1), Plats varchar(1), Projektkod varchar(1), Projektledare varchar(1), Projektnamn varchar(1), Raä Dnr varchar(1), SiteId varchar(1), Slutdatum varchar(1), Undersökningstyp varchar(1), Uppdragsgivare varchar(1), _reader_error varchar(59)
    -> FeatureMerger [REQUESTOR]
FeatureMerger
    ATTR_ACCUM_MODE = Merge Supplier
    ATTR_CONFLICT_RES = Use Requestor
    IGNORE_NULLS = No
    JOIN_KEYS = @Value(databas) @Value(path_rootname) AUTO
    MERGE_TYPE = Attributes Only
    PROCESS_DUPS = NO
    REJECT_NULL_MISSING_KEYS = No
    SUPPLIERS_FIRST = No
    MERGED -> AttributeManager
AttributeManager
    ATTR_TABLE:
      SET_TO restore = ""C:/Program Files/PostgreSQL/11/bin/pg_restore.exe" -h $(server)  -p $(port) -U $(user)  -w -d  @Value(databas) -O -x -c --no-security-labels "@Value(path_windows)""
      SET_TO createdb = ""C:/Program Files/PostgreSQL/11/bin/psql.exe" -h $(server)  -p $(port) -U $(user) -c "CREATE DATABASE  @Value(databas) WITH TEMPLATE = urdar_template ENCODING = 'UTF8'"
    -> SystemCaller_3
SystemCaller_3
    CMD = ""C:/Program Files/PostgreSQL/11/bin/psql.exe" -h $(server)  -p $(port) -U $(user) -c "CREATE DATABASE  @Value(databas) WITH TEMPLATE = urdar_template ENCODING = 'UTF8'"
    -> SystemCaller
SystemCaller
    ATTR = hejda
    CMD = ""C:/Program Files/PostgreSQL/11/bin/pg_restore.exe" -h $(server)  -p $(port) -U $(user)  -w -d @Value(databas) -O -x -c --no-security-labels "@Value(path_windows)""
