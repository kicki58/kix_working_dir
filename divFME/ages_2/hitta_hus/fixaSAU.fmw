FME workspace fixaSAU.fmw

Parameters:
- SourceDataset_OGCGEOPACKAGE = C:\ny_slask\hittade_hus_utan_urdar20260225.gpkg   # GeoPackage File
- DestDataset_OGCGEOPACKAGE = C:\ny_slask\hittade_hus_utan_urdar20260225_2.gpkg   # GeoPackage File

Readers:
- OGCGEOPACKAGE_1: OGCGEOPACKAGE from $(SourceDataset_OGCGEOPACKAGE)

Writers:
- OGCGEOPACKAGE_2: OGCGEOPACKAGE to $(DestDataset_OGCGEOPACKAGE)

hus_med_egen_geometri (reader OGCGEOPACKAGE_1)
    attributes: hus_gpkg-name text(50), hus_utforare text(200), hus_intrasisid int, hus_name text, hus_class text, hus_subclass text, hus_color int, hus_geometry_count int, hus_attributes text, hus_object_id int, hus_uppdragsnummer text(200), hus_sweref_klart text(200), hus_klar_for_ages text(200), hus_publicerad_pa_ages text(200), object_id mediumint, symbolid mediumint, geoobjectid mediumint, spatial_type text, id int,PrimaryKey
    -> Tester
hus_utan_egen_geometri (reader OGCGEOPACKAGE_1)
    attributes: hus_gpkg-name text(50), hus_utforare text(200), hus_uppdragsnummer text(200), hus_intrasisid int, hus_name text, hus_class text, hus_subclass text, hus_color int, hus_geometry_count int, hus_attributes text, hus_object_id int, hus_sweref_klart text(200), hus_klar_for_ages text(200), hus_publicerad_pa_ages text(200), id int,PrimaryKey
    -> Tester
stolphal_med relation_till_hus (reader OGCGEOPACKAGE_1)
    attributes: hus_gpkg-name text(50), hus_utforare text(200), hus_uppdragsnummer text(200), stolp_utforare text(200), stolp_uppdragsnummer text(200), stolp_sweref_klart text(200), stolp_klar_for_ages text(200), stolp_publicerad_pa_ages text(200), object_id mediumint, symbolid mediumint, geoobjectid mediumint, spatial_type text, stolp_gpkg-name text(50), stolp_intrasisid int, stolp_name text, stolp_class text, stolp_subclass text, stolp_color int, stolp_geometry_count int, stolp_attributes text, stolp_object_id int, base_id mediumint, related_id mediumint, base_text text(30), related_text text(30), id int, hus_intrasisid int, hus_name text, hus_class text, hus_subclass text,
      hus_color int, hus_geometry_count int, hus_attributes text, hus_object_id int, hus_sweref_klart text(200), hus_klar_for_ages text(200), hus_publicerad_pa_ages text(200), id_0 int,PrimaryKey
    -> Tester
stolphal_utan_relation_till_hus (reader OGCGEOPACKAGE_1)
    attributes: stolp_gpkg-name text(50), stolp_intrasisid int, stolp_name text, stolp_class text, stolp_subclass text, stolp_color int, stolp_geometry_count int, stolp_attributes text, stolp_object_id int, object_id mediumint, symbolid mediumint, geoobjectid mediumint, spatial_type text, base_id mediumint, related_id mediumint, base_text text(30), related_text text(30), id int, id_0 int,PrimaryKey
    -> Tester
Tester
    BOOL_OP = OR
    TEST_CLAUSE:
      TEST @Value(stolp_utforare) = U
      TEST @Value(hus_utforare) = U
    TEST_MODE = TEST
    PASSED -> AttributeManager
    FAILED -> FeatureTypeFilter_2
AttributeManager
    ATTR_TABLE = SET_TO hus_utforare (varchar(3)) = SAU
    -> FeatureTypeFilter
FeatureTypeFilter
    ATTRIBUTES = <Blank>,<Unfiltered>,hus_med_egen_geometri,stolphal_med relation_till_hus,hus_utan_egen_geometri,stolphal_utan_relation_till_hus
    ATTRIBUTE_INFO = hus_med_egen_geometri,hus_gpkg-name,hus_utforare,hus_intrasisid,hus_name,hus_class,hus_subclass,hus_color,hus_geometry_count,hus_attributes,hus_object_id,hus_uppdragsnummer,hus_sweref_klart,hus_klar_for_ages,hus_publicerad_pa_ages,object_id,symbolid,geoobjectid,spatial_type,id,hus_utan_egen_geometri,hus_gpkg-name,hus_utforare,hus_uppdragsnummer,hus_intrasisid,hus_name,hus_class,hus_subclass,hus_color,hus_geometry_count,hus_attributes,hus_object_id,hus_sweref_klart,hus_klar_for_ages,hus_publicerad_pa_ages,id,stolphal_med relation_till_hus,hus_gpkg-name,hus_utforare,hus_uppdragsnummer,stolp_utforare,stolp_uppdragsnummer,stolp_sweref_klart,stolp_klar_for_ages,stolp_publicerad_pa_ages,object_id,symbolid,geoobjectid,spatial_type,stolp_gpkg-name,stolp_intrasisid,stolp_name,stolp_class,stolp_subclass,stolp_color,stolp_geometry_count,stolp_attributes,stolp_object_id,base_id,related_id,base_text,related_text,id,hus_intrasisid,hus_name,hus_class,hus_subclass,hus_color,hus_geometry_count,hus_attributes,hus_object_id,hus_sweref_klart,hus_klar_for_ages,hus_publicerad_pa_ages,id_0,stolphal_utan_relation_till_hus,stolp_gpkg-name,stolp_intrasisid,stolp_name,stolp_class,stolp_subclass,stolp_color,stolp_geometry_count,stolp_attributes,stolp_object_id,object_id,symbolid,geoobjectid,spatial_type,base_id,related_id,base_text,related_text,id,id_0
    hus_med_egen_geometri -> hus_utan_egen_geometri (writer OGCGEOPACKAGE_2)
    stolphal_med relation_till_hus -> stolphal_med relation_till_hus (writer OGCGEOPACKAGE_2)
    hus_utan_egen_geometri -> hus_med_egen_geometri (writer OGCGEOPACKAGE_2)
    stolphal_utan_relation_till_hus -> stolphal_utan_relation_till_hus (writer OGCGEOPACKAGE_2)
FeatureTypeFilter_2
    ATTRIBUTES = <Blank>,<Unfiltered>,hus_med_egen_geometri,stolphal_med relation_till_hus,hus_utan_egen_geometri,stolphal_utan_relation_till_hus
    ATTRIBUTE_INFO = hus_med_egen_geometri,hus_gpkg-name,hus_utforare,hus_intrasisid,hus_name,hus_class,hus_subclass,hus_color,hus_geometry_count,hus_attributes,hus_object_id,hus_uppdragsnummer,hus_sweref_klart,hus_klar_for_ages,hus_publicerad_pa_ages,object_id,symbolid,geoobjectid,spatial_type,id,hus_utan_egen_geometri,hus_gpkg-name,hus_utforare,hus_uppdragsnummer,hus_intrasisid,hus_name,hus_class,hus_subclass,hus_color,hus_geometry_count,hus_attributes,hus_object_id,hus_sweref_klart,hus_klar_for_ages,hus_publicerad_pa_ages,id,stolphal_med relation_till_hus,hus_gpkg-name,hus_utforare,hus_uppdragsnummer,stolp_utforare,stolp_uppdragsnummer,stolp_sweref_klart,stolp_klar_for_ages,stolp_publicerad_pa_ages,object_id,symbolid,geoobjectid,spatial_type,stolp_gpkg-name,stolp_intrasisid,stolp_name,stolp_class,stolp_subclass,stolp_color,stolp_geometry_count,stolp_attributes,stolp_object_id,base_id,related_id,base_text,related_text,id,hus_intrasisid,hus_name,hus_class,hus_subclass,hus_color,hus_geometry_count,hus_attributes,hus_object_id,hus_sweref_klart,hus_klar_for_ages,hus_publicerad_pa_ages,id_0,stolphal_utan_relation_till_hus,stolp_gpkg-name,stolp_intrasisid,stolp_name,stolp_class,stolp_subclass,stolp_color,stolp_geometry_count,stolp_attributes,stolp_object_id,object_id,symbolid,geoobjectid,spatial_type,base_id,related_id,base_text,related_text,id,id_0
    hus_med_egen_geometri -> hus_med_egen_geometri (writer OGCGEOPACKAGE_2)
    stolphal_med relation_till_hus -> stolphal_med relation_till_hus (writer OGCGEOPACKAGE_2)
    hus_utan_egen_geometri -> hus_utan_egen_geometri (writer OGCGEOPACKAGE_2)
    stolphal_utan_relation_till_hus -> stolphal_utan_relation_till_hus (writer OGCGEOPACKAGE_2)
hus_utan_egen_geometri (writer OGCGEOPACKAGE_2)
    attributes: hus_gpkg-name text(50), hus_utforare text(200), hus_uppdragsnummer text(200), hus_intrasisid int, hus_name text, hus_class text, hus_subclass text, hus_color int, hus_geometry_count int, hus_attributes text, hus_object_id int, hus_sweref_klart text(200), hus_klar_for_ages text(200), hus_publicerad_pa_ages text(200), id int
stolphal_med relation_till_hus (writer OGCGEOPACKAGE_2)
    attributes: hus_gpkg-name text(50), hus_utforare text(200), hus_uppdragsnummer text(200), stolp_utforare text(200), stolp_uppdragsnummer text(200), stolp_sweref_klart text(200), stolp_klar_for_ages text(200), stolp_publicerad_pa_ages text(200), object_id mediumint, symbolid mediumint, geoobjectid mediumint, spatial_type text, stolp_gpkg-name text(50), stolp_intrasisid int, stolp_name text, stolp_class text, stolp_subclass text, stolp_color int, stolp_geometry_count int, stolp_attributes text, stolp_object_id int, base_id mediumint, related_id mediumint, base_text text(30), related_text text(30), id int, hus_intrasisid int, hus_name text, hus_class text, hus_subclass text,
      hus_color int, hus_geometry_count int, hus_attributes text, hus_object_id int, hus_sweref_klart text(200), hus_klar_for_ages text(200), hus_publicerad_pa_ages text(200), id_0 int
hus_med_egen_geometri (writer OGCGEOPACKAGE_2)
    attributes: hus_gpkg-name text(50), hus_utforare text(200), hus_intrasisid int, hus_name text, hus_class text, hus_subclass text, hus_color int, hus_geometry_count int, hus_attributes text, hus_object_id int, hus_uppdragsnummer text(200), hus_sweref_klart text(200), hus_klar_for_ages text(200), hus_publicerad_pa_ages text(200), object_id mediumint, symbolid mediumint, geoobjectid mediumint, spatial_type text, id int
stolphal_utan_relation_till_hus (writer OGCGEOPACKAGE_2)
    attributes: stolp_gpkg-name text(50), stolp_intrasisid int, stolp_name text, stolp_class text, stolp_subclass text, stolp_color int, stolp_geometry_count int, stolp_attributes text, stolp_object_id int, object_id mediumint, symbolid mediumint, geoobjectid mediumint, spatial_type text, base_id mediumint, related_id mediumint, base_text text(30), related_text text(30), id int, id_0 int
