FME workspace typlistaRAA.fmw

Parameters:
- DestDataset_XLSXW = $(FME_MF_DIR)RAAlista2.xlsx   # Destination Microsoft Excel File
- START = 5000   # Count Start
- NUM = 1000   # Number to Create

Writers:
- XLSXW_1: XLSXW to $(DestDataset_XLSXW)

Creator
    GEOMTYPE = Geometry Object
    NUM = $(NUM)
    CREATED -> Counter
Counter
    CNT_ATTR = _count
    DOMAIN = counter
    SCOPE = Global
    START = $(START)
    -> AttributeManager_2
AttributeManager_2
    ATTR_TABLE = SET_TO link (varchar(200)) = https://app.raa.se/open/fornsok/lamningstyp/definition?id=@Value(_count)
    -> HTTPCaller
HTTPCaller
    CLIENT_CERTIFICATE_TYPE = NONE
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = utf-8
    TARGET_URL = @Value(link)
    TEST_DIALOG_PARAMETERS_FOR_RESPONSE = authConnection;<Unused> authEnabled;false authMethod;<Unused> authPassword;<Unused> authUsername;<Unused> contentType; method;GET multipartContentType;<Unused> requestUrl;https://samlingar.shm.se/sok?type=term&query=Utm%C3%A4rkande%20egenskap%20(fyndort) uploadData; verifySslCert;Yes version;HTTP_2
    TEST_DIALOG_RESPONSE_PREVIEW =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
    TEST_DIALOG_RESPONSE_STATUS:
      HTTP/1.1 200 OK
      Download Size: 31606 bytes
      Total Transfer Time: 69 ms
    TRANSFER_TIMEOUT_LENGTH = 90
    USE_COOKIES = No
    VERIFY_SSL_CERTIFICATES = Yes
    -> Tester
Tester
    BOOL_OP = OR
    TEST_CLAUSE = CASE_INSENSITIVE_TEST @Value(_response_body) CONTAINS Sidan hittades inte
    TEST_MODE = TEST
    FAILED -> HTMLExtractor
HTMLExtractor
    _FME_USE_PARSER = html.parser
    _FME_VERIFY_HTTPS = yes
    ___fme_htmlex_html_field = @Value(_response_body)
    ___fme_htmlex_html_specification = Content
    ___fme_htmlex_result_type_name = LIST_ATTR
    ___fme_htmlex_search_table = semibold [class="tw-font-semibold"] All Text text [style="color: black;"] All Text p p All Text
    Results -> ListConcatenator
ListConcatenator
    DROP_EMPTY_PARTS = No
    LIST_ATTR = p{}
    SEP = " "
    VAL_ATTR = definition
    -> ListConcatenator_2
ListConcatenator_2
    DROP_EMPTY_PARTS = No
    LIST_ATTR = text{}
    SEP = " "
    VAL_ATTR = def2
    -> AttributeManager
AttributeManager
    ATTR_TABLE:
      SET_TO Typ (varchar(200)) = @Value(semibold{0})
      RENAME_SET_VALUE definition > Definition (buffer)
      RENAME_SET_VALUE def2 > Kommentar (buffer)
      REMOVE _creation_instance (uint64)
      REMOVE _count (int64)
      REMOVE _response_body (buffer)
      REMOVE _http_status_code (buffer)
      REMOVE text{} (varchar(200))
      REMOVE p{} (varchar(200))
    -> AttributeRemover
AttributeRemover
    LIST_ATTRS = semibold{}
    -> Sheet1 (writer XLSXW_1)
Sheet1 (writer XLSXW_1)
    attributes: Typ string(200), Definition string(20), Kommentar string(20), link string(200)
