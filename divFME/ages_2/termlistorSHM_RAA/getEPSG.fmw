FME workspace getEPSG.fmw

Parameters:
- SourceDataset_XLSXR = $(FME_MF_DIR)srid_import.xlsx   # Source Microsoft Excel File(s)

Readers:
- XLSXR_1: XLSXR from $(SourceDataset_XLSXR)

Blad1 (reader XLSXR_1)
    attributes: srid number(4,0)
    -> HTTPCaller
HTTPCaller
    CLIENT_CERTIFICATE_TYPE = NONE
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = fme-system
    TARGET_URL = https://www.opengis.net/def/crs/EPSG/0/@Value(srid)
    TRANSFER_TIMEOUT_LENGTH = 90
    USE_COOKIES = No
    VERIFY_SSL_CERTIFICATES = Yes
    -> XMLXQueryExtractor
XMLXQueryExtractor
    QUERY_EXPR:
      declare namespace gml   = "http://www.opengis.net/gml/3.2";
      declare namespace epsg  = "urn:x-ogp:spec:schema-xsd:EPSG:2.3:dataset";
      declare namespace xlink = "http://www.w3.org/1999/xlink";

        gml:ProjectedCRS[@gml:id ]
            /gml:metaDataProperty/epsg:CommonMetaData/epsg:alias/@alias/string()
    RESULT_ATTRIBUTE = _result
    RESULT_TYPE = CSV
    SEPARATOR_VALUE = ,
    WRITE_XML_HEADER = No
    XML_ATTR = _response_body
    XML_REMOVE_SOURCE_ATTR = No
    XML_TYPE = xml_attr
    XQUERY_TYPE = xquery_expression
