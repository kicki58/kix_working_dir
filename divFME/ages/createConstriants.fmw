FME workspace createConstriants.fmw

Parameters:
- PostgreSQL_CONNECTION = uuc-srv390_ages_5434   # Connection

Creator
    GEOMTYPE = Geometry Object
    NUM = 1
    CREATED -> SQLExecutor_2 [INITIATOR]
SQLExecutor_2
    COMBINE_ATTRS = Result Attributes Only
    COMBINE_GEOM = Initiator Geometry Only
    DATASET = $(PostgreSQL_CONNECTION)
    FORMAT = POSTGRES
    OUTPUT_FEATURES = DATA_ONLY
    POSTGRES_CREATE_FEATURE_TABLES_FROM_DATA = Yes
    POSTGRES_NAMED_CONNECTION = $(PostgreSQL_CONNECTION)
    POSTGRES_QUERY_FEATURE_TYPES_FOR_MERGE_FILTERS = Yes
    POSTGRES_READ_TIME_WITH_TIMEZONE = Yes
    SQL_STATEMENT:
      FME_SQL_DELIMITER ;
      ALTER TABLE IF EXISTS ages.rel2uppdrag
          ADD CONSTRAINT fk_geodata_info FOREIGN KEY (gpkg_uuid)
          REFERENCES ages.geodata_info (gpkg_uuid) MATCH SIMPLE
          ON UPDATE NO ACTION
          ON DELETE NO ACTION
          NOT VALID;
