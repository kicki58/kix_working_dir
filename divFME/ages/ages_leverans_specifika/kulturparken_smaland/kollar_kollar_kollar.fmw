FME workspace kollar_kollar_kollar.fmw

Parameters:
- SourceDataset_XLSXR = \\argos.storage.uu.se\MyFolder$\krima354\kicki_arbetsfiler\kulturparken_smaland\Projektprotokoll_lev1.xlsx   # Source Microsoft Excel File(s)
- SourceDataset_PATH_5 = \\argos.storage.uu.se\MyFolder$\krima354\kicki_arbetsfiler\kulturparken_smaland   # INCLUDE_WEB_BROWSER Source Folder and File Pathnames Folder
- SourceDataset_PATH = \\argos.storage.uu.se\MyFolder$\krima354\kicki_arbetsfiler\kulturparken_smaland\1_alla   # INCLUDE_WEB_BROWSER Source Folder and File Pathnames Folder
- SourceDataset_XLSXR_5 = \\argos.storage.uu.se\MyFolder$\krima354\kicki_arbetsfiler\kulturparken_smaland\konverteringsprotokoll_i2_i3.xlsx   # Source Microsoft Excel File(s)
- SourceDataset_XLSXR_4 = \\argos.storage.uu.se\MyFolder$\krima354\kicki_arbetsfiler\kulturparken_smaland\Lista över intrasisproj överförda till Arkiv-arkeologi (1).xls   # Source Microsoft Excel File(s)
- SourceDataset_PATH_7 = C:\Users\krima354\Downloads\MSQL_bak_filer (1)   # INCLUDE_WEB_BROWSER Source Folder and File Pathnames Folder
- SourceDataset_PATH_6 = K:\kulturparken_smaland\gor_om   # INCLUDE_WEB_BROWSER Source Folder and File Pathnames Folder

Readers:
- XLSXR_1: XLSXR from $(SourceDataset_XLSXR)
- PATH_1: PATH from $(SourceDataset_PATH)
- PATH_2: PATH from $(SourceDataset_PATH_5)
- XLSXR_2: XLSXR from $(SourceDataset_XLSXR_5)
- XLSXR_3: XLSXR from $(SourceDataset_XLSXR_4)
- PATH_3: PATH from $(SourceDataset_PATH_7)
- PATH_4: PATH from $(SourceDataset_PATH_6)

PATH (reader PATH_1)
    attributes: path_unix buffer, path_windows buffer, path_rootname buffer, path_filename buffer, path_extension buffer, path_directory_unix buffer, path_directory_windows buffer, path_type char(10)
    -> FeatureMerger [SUPPLIER]
Blad1 (reader XLSXR_3)
    attributes: SM Intrasisprojekt char(129), Säkerhetskopierad 090605 char(25), Återställd på public 090605 char(30), Problem char(47), GIS-data i shaper inlagda i Arkiv Arkeologi char(46), Data till Swedigarch char(2), SM Rapport char(36), H string, I string, J string, K string, L string, M string, N string, O string, P string, Q string, R string, S string, T string, U string, V string, W string, X string, Y string, Z string, AA string, AB string, AC string, AD string,
      AE string, AF string, AG string, AH string, AI string, AJ string, AK string, AL string, AM string, AN string, AO string, AP string, AQ string, AR string, AS string, AT string, AU string, AV string, AW string, AX string, AY string, AZ string, BA string, BB string, BC string, BD string, BE string, BF string, BG string, BH string,
      BI string, BJ string, BK string, BL string, BM string, BN string, BO string, BP string, BQ string, BR string, BS string, BT string, BU string, BV string, BW string, BX string, BY string, BZ string, CA string, CB string, CC string, CD string, CE string, CF string, CG string, CH string, CI string, CJ string, CK string, CL string,
      CM string, CN string, CO string, CP string, CQ string, CR string, CS string, CT string, CU string, CV string, CW string, CX string, CY string, CZ string, DA string, DB string, DC string, DD string, DE string, DF string, DG string, DH string, DI string, DJ string, DK string, DL string, DM string, DN string, DO string, DP string,
      DQ string, DR string, DS string, DT string, DU string, DV string, DW string, DX string, DY string, DZ string, EA string, EB string, EC string, ED string, EE string, EF string, EG string, EH string, EI string, EJ string, EK string, EL string, EM string, EN string, EO string, EP string, EQ string, ER string, ES string, ET string,
      EU string, EV string, EW string, EX string, EY string, EZ string, FA string, FB string, FC string, FD string, FE string, FF string, FG string, FH string, FI string, FJ string, FK string, FL string, FM string, FN string, FO string, FP string, FQ string, FR string, FS string, FT string, FU string, FV string, FW string, FX string,
      FY string, FZ string, GA string, GB string, GC string, GD string, GE string, GF string, GG string, GH string, GI string, GJ string, GK string, GL string, GM string, GN string, GO string, GP string, GQ string, GR string, GS string, GT string, GU string, GV string, GW string, GX string, GY string, GZ string, HA string, HB string,
      HC string, HD string, HE string, HF string, HG string, HH string, HI string, HJ string, HK string, HL string, HM string, HN string, HO string, HP string, HQ string, HR string, HS string, HT string, HU string, HV string, HW string, HX string, HY string, HZ string, IA string, IB string, IC string, ID string, IE string, IF string,
      IG string, IH string, II string, IJ string, IK string, IL string, IM string, IN string, IO string, IP string, IQ string, IR string, IS string, IT string, IU string, IV string
    -> AttributeManager
AttributeManager
    ATTR_TABLE:
      SET_TO SM Intrasisprojekt (varchar(129)) = sm@ReplaceString(@Value(SM Intrasisprojekt),:,,caseSensitive=TRUE)
      REMOVE H (buffer)
      REMOVE I (buffer)
      REMOVE J (buffer)
      REMOVE K (buffer)
      REMOVE L (buffer)
      REMOVE M (buffer)
      REMOVE N (buffer)
      REMOVE O (buffer)
      REMOVE P (buffer)
      REMOVE Q (buffer)
      REMOVE R (buffer)
      REMOVE S (buffer)
      REMOVE T (buffer)
      REMOVE U (buffer)
      REMOVE V (buffer)
      REMOVE W (buffer)
      REMOVE X (buffer)
      REMOVE Y (buffer)
      REMOVE Z (buffer)
      REMOVE AA (buffer)
      REMOVE AB (buffer)
      REMOVE AC (buffer)
      REMOVE AD (buffer)
      REMOVE AE (buffer)
      REMOVE AF (buffer)
      REMOVE AG (buffer)
      REMOVE AH (buffer)
      REMOVE AI (buffer)
      REMOVE AJ (buffer)
      REMOVE AK (buffer)
      REMOVE AL (buffer)
      REMOVE AM (buffer)
      REMOVE AN (buffer)
      REMOVE AO (buffer)
      REMOVE AP (buffer)
      REMOVE AQ (buffer)
      REMOVE AR (buffer)
      REMOVE AS (buffer)
      REMOVE AT (buffer)
      REMOVE AU (buffer)
      REMOVE AV (buffer)
      REMOVE AW (buffer)
      REMOVE AX (buffer)
      REMOVE AY (buffer)
      REMOVE AZ (buffer)
      REMOVE BA (buffer)
      REMOVE BB (buffer)
      REMOVE BC (buffer)
      REMOVE BD (buffer)
      REMOVE BE (buffer)
      REMOVE BF (buffer)
      REMOVE BG (buffer)
      REMOVE BH (buffer)
      REMOVE BI (buffer)
      REMOVE BJ (buffer)
      REMOVE BK (buffer)
      REMOVE BL (buffer)
      REMOVE BM (buffer)
      REMOVE BN (buffer)
      REMOVE BO (buffer)
      REMOVE BP (buffer)
      REMOVE BQ (buffer)
      REMOVE BR (buffer)
      REMOVE BS (buffer)
      REMOVE BT (buffer)
      REMOVE BU (buffer)
      REMOVE BV (buffer)
      REMOVE BW (buffer)
      REMOVE BX (buffer)
      REMOVE BY (buffer)
      REMOVE BZ (buffer)
      REMOVE CA (buffer)
      REMOVE CB (buffer)
      REMOVE CC (buffer)
      REMOVE CD (buffer)
      REMOVE CE (buffer)
      REMOVE CF (buffer)
      REMOVE CG (buffer)
      REMOVE CH (buffer)
      REMOVE CI (buffer)
      REMOVE CJ (buffer)
      REMOVE CK (buffer)
      REMOVE CL (buffer)
      REMOVE CM (buffer)
      REMOVE CN (buffer)
      REMOVE CO (buffer)
      REMOVE CP (buffer)
      REMOVE CQ (buffer)
      REMOVE CR (buffer)
      REMOVE CS (buffer)
      REMOVE CT (buffer)
      REMOVE CU (buffer)
      REMOVE CV (buffer)
      REMOVE CW (buffer)
      REMOVE CX (buffer)
      REMOVE CY (buffer)
      REMOVE CZ (buffer)
      REMOVE DA (buffer)
      REMOVE DB (buffer)
      REMOVE DC (buffer)
      REMOVE DD (buffer)
      REMOVE DE (buffer)
      REMOVE DF (buffer)
      REMOVE DG (buffer)
      REMOVE DH (buffer)
      REMOVE DI (buffer)
      REMOVE DJ (buffer)
      REMOVE DK (buffer)
      REMOVE DL (buffer)
      REMOVE DM (buffer)
      REMOVE DN (buffer)
      REMOVE DO (buffer)
      REMOVE DP (buffer)
      REMOVE DQ (buffer)
      REMOVE DR (buffer)
      REMOVE DS (buffer)
      REMOVE DT (buffer)
      REMOVE DU (buffer)
      REMOVE DV (buffer)
      REMOVE DW (buffer)
      REMOVE DX (buffer)
      REMOVE DY (buffer)
      REMOVE DZ (buffer)
      REMOVE EA (buffer)
      REMOVE EB (buffer)
      REMOVE EC (buffer)
      REMOVE ED (buffer)
      REMOVE EE (buffer)
      REMOVE EF (buffer)
      REMOVE EG (buffer)
      REMOVE EH (buffer)
      REMOVE EI (buffer)
      REMOVE EJ (buffer)
      REMOVE EK (buffer)
      REMOVE EL (buffer)
      REMOVE EM (buffer)
      REMOVE EN (buffer)
      REMOVE EO (buffer)
      REMOVE EP (buffer)
      REMOVE EQ (buffer)
      REMOVE ER (buffer)
      REMOVE ES (buffer)
      REMOVE ET (buffer)
      REMOVE EU (buffer)
      REMOVE EV (buffer)
      REMOVE EW (buffer)
      REMOVE EX (buffer)
      REMOVE EY (buffer)
      REMOVE EZ (buffer)
      REMOVE FA (buffer)
      REMOVE FB (buffer)
      REMOVE FC (buffer)
      REMOVE FD (buffer)
      REMOVE FE (buffer)
      REMOVE FF (buffer)
      REMOVE FG (buffer)
      REMOVE FH (buffer)
      REMOVE FI (buffer)
      REMOVE FJ (buffer)
      REMOVE FK (buffer)
      REMOVE FL (buffer)
      REMOVE FM (buffer)
      REMOVE FN (buffer)
      REMOVE FO (buffer)
      REMOVE FP (buffer)
      REMOVE FQ (buffer)
      REMOVE FR (buffer)
      REMOVE FS (buffer)
      REMOVE FT (buffer)
      REMOVE FU (buffer)
      REMOVE FV (buffer)
      REMOVE FW (buffer)
      REMOVE FX (buffer)
      REMOVE FY (buffer)
      REMOVE FZ (buffer)
      REMOVE GA (buffer)
      REMOVE GB (buffer)
      REMOVE GC (buffer)
      REMOVE GD (buffer)
      REMOVE GE (buffer)
      REMOVE GF (buffer)
      REMOVE GG (buffer)
      REMOVE GH (buffer)
      REMOVE GI (buffer)
      REMOVE GJ (buffer)
      REMOVE GK (buffer)
      REMOVE GL (buffer)
      REMOVE GM (buffer)
      REMOVE GN (buffer)
      REMOVE GO (buffer)
      REMOVE GP (buffer)
      REMOVE GQ (buffer)
      REMOVE GR (buffer)
      REMOVE GS (buffer)
      REMOVE GT (buffer)
      REMOVE GU (buffer)
      REMOVE GV (buffer)
      REMOVE GW (buffer)
      REMOVE GX (buffer)
      REMOVE GY (buffer)
      REMOVE GZ (buffer)
      REMOVE HA (buffer)
      REMOVE HB (buffer)
      REMOVE HC (buffer)
      REMOVE HD (buffer)
      REMOVE HE (buffer)
      REMOVE HF (buffer)
      REMOVE HG (buffer)
      REMOVE HH (buffer)
      REMOVE HI (buffer)
      REMOVE HJ (buffer)
      REMOVE HK (buffer)
      REMOVE HL (buffer)
      REMOVE HM (buffer)
      REMOVE HN (buffer)
      REMOVE HO (buffer)
      REMOVE HP (buffer)
      REMOVE HQ (buffer)
      REMOVE HR (buffer)
      REMOVE HS (buffer)
      REMOVE HT (buffer)
      REMOVE HU (buffer)
      REMOVE HV (buffer)
      REMOVE HW (buffer)
      REMOVE HX (buffer)
      REMOVE HY (buffer)
      REMOVE HZ (buffer)
      REMOVE IA (buffer)
      REMOVE IB (buffer)
      REMOVE IC (buffer)
      REMOVE ID (buffer)
      REMOVE IE (buffer)
      REMOVE IF (buffer)
      REMOVE IG (buffer)
      REMOVE IH (buffer)
      REMOVE II (buffer)
      REMOVE IJ (buffer)
      REMOVE IK (buffer)
      REMOVE IL (buffer)
      REMOVE IM (buffer)
      REMOVE IN (buffer)
      REMOVE IO (buffer)
      REMOVE IP (buffer)
      REMOVE IQ (buffer)
      REMOVE IR (buffer)
      REMOVE IS (buffer)
      REMOVE IT (buffer)
      REMOVE IU (buffer)
      REMOVE IV (buffer)
sheet6 (reader XLSXR_1)
    attributes: Filnamn databas char(43), Kommentar geopackage char(101), SM-intrasis projekt char(59), SM rapport char(36), Rapport länk char(215), Uppdragsnummer char(36), Uppdragnummmer_updated / kommentar char(66), Uppgett koordinatsystem number(4,0), Faktiskt koordinatsystem number(4,0), Sweref klart char(2), Koordinatsystem/geolokalisering kommentar char(1), Manuellt rektifierad char(1), Rektifiering precision char(1), Rektifiering kommentar char(1), Sekretesskontroll godkänd char(1), Klar för AGES char(1), Publicerad på AGES char(1)
    -> FeatureMerger [REQUESTOR]
FeatureMerger
    ATTR_ACCUM_MODE = Merge Supplier
    ATTR_CONFLICT_RES_LOOKUP = REQUESTOR_IF_CONFLICT
    IGNORE_NULLS = No
    JOIN_KEYS = @Value(Filnamn databas) @Value(path_rootname) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    UNMERGED_REQUESTOR -> FeatureMerger_2 [REQUESTOR]
PATH (reader PATH_2)
    attributes: path_unix buffer, path_windows buffer, path_rootname buffer, path_filename buffer, path_extension buffer, path_directory_unix buffer, path_directory_windows buffer, path_type char(10)
    -> FeatureMerger_2 [SUPPLIER]
FeatureMerger_2
    ATTR_ACCUM_MODE = Merge Supplier
    ATTR_CONFLICT_RES_LOOKUP = REQUESTOR_IF_CONFLICT
    IGNORE_NULLS = No
    JOIN_KEYS = @Value(Filnamn databas) @Value(path_rootname) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    UNMERGED_REQUESTOR -> FeatureMerger_3 [REQUESTOR]
SQLCreator
    DATASET = postgres@uuc-srv390_5432
    EXPOSED_ATTRIBUTE_LIST = datname
    FORMAT = POSTGRES
    OUTPUT_FEATURES = DATA_ONLY
    POSTGRES_CREATE_FEATURE_TABLES_FROM_DATA = Yes
    POSTGRES_NAMED_CONNECTION = postgres@uuc-srv390_5432
    POSTGRES_QUERY_FEATURE_TYPES_FOR_MERGE_FILTERS = Yes
    POSTGRES_READ_TIME_WITH_TIMEZONE = Yes
    POSTGRES_SCHEMAS_FOR_TABLE_LISTING = public
    SQL_STATEMENT = "SELECT datname FROM pg_database;\n"
    RESULT -> FeatureMerger_3 [SUPPLIER]
FeatureMerger_3
    ATTR_ACCUM_MODE = Merge Supplier
    ATTR_CONFLICT_RES_LOOKUP = REQUESTOR_IF_CONFLICT
    IGNORE_NULLS = No
    JOIN_KEYS = @Value(Filnamn databas) @Value(datname) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    UNMERGED_REQUESTOR -> FeatureMerger_4 [REQUESTOR]
protokoll (reader XLSXR_2)
    attributes: intrasis_db_name char(14), ant char(21), konverterat till i2 string, SM Intrasisprojekt char(59), Säkerhetskopierad 090605 char(16), Återställd på public 090605 char(16), Problem char(38), GIS-data i shaper inlagda i Arkiv Arkeologi char(46), Data till Swedigarch char(2), SM Rapport char(36)
    -> FeatureMerger_4 [SUPPLIER]
FeatureMerger_4
    ATTR_ACCUM_MODE = Merge Supplier
    ATTR_CONFLICT_RES_LOOKUP = REQUESTOR_IF_CONFLICT
    IGNORE_NULLS = No
    JOIN_KEYS = @Value(Filnamn databas) @Value(intrasis_db_name) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    UNMERGED_REQUESTOR -> FeatureMerger_6 [REQUESTOR]
PATH (reader PATH_3)
    attributes: path_unix buffer, path_windows buffer, path_rootname buffer, path_filename buffer, path_extension buffer, path_directory_unix buffer, path_directory_windows buffer, path_type char(10)
    -> AttributeManager_2
AttributeManager_2
    ATTR_TABLE = SET_TO path_rootname (buffer) = @LowerCase(@Value(path_rootname))
    -> FeatureMerger_6 [SUPPLIER]
FeatureMerger_6
    ATTR_ACCUM_MODE = Merge Supplier
    ATTR_CONFLICT_RES_LOOKUP = REQUESTOR_IF_CONFLICT
    IGNORE_NULLS = No
    JOIN_KEYS = @Value(Filnamn databas) @Value(path_rootname) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    UNMERGED_REQUESTOR -> FeatureMerger_7 [REQUESTOR]
SQLCreator_2
    DATASET = uuc-srv_1434
    EXPOSED_ATTRIBUTE_LIST = name
    FORMAT = SQLSERVER
    GEOMETRY_TYPES = ",fme_no_geom"
    OUTPUT_FEATURES = DATA_ONLY
    SQLSERVER_APPLICATION_INTENT = ReadWrite
    SQLSERVER_COMMAND_TIMEOUT = 30
    SQLSERVER_CREATE_FEATURE_TABLES_FROM_DATA = Yes
    SQLSERVER_NAMED_CONNECTION = uuc-srv_1434
    SQLSERVER_QUERY_FEATURE_TYPES_FOR_MERGE_FILTERS = Yes
    SQL_STATEMENT = SELECT name FROM master.sys.databases
    RESULT -> AttributeManager_3
AttributeManager_3
    ATTR_TABLE = SET_TO name (varchar(128)) = @LowerCase(@Value(name))
    -> FeatureMerger_7 [SUPPLIER]
FeatureMerger_7
    ATTR_ACCUM_MODE = Merge Supplier
    ATTR_CONFLICT_RES_LOOKUP = REQUESTOR_IF_CONFLICT
    IGNORE_NULLS = No
    JOIN_KEYS = @Value(Filnamn databas) @Value(name) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    UNMERGED_REQUESTOR -> FeatureMerger_8 [REQUESTOR]
PATH (reader PATH_4)
    attributes: path_unix buffer, path_windows buffer, path_rootname buffer, path_filename buffer, path_extension buffer, path_directory_unix buffer, path_directory_windows buffer, path_type char(10)
    -> AttributeManager_4
AttributeManager_4
    ATTR_TABLE = SET_TO path_rootname (buffer) = @LowerCase(@Value(path_rootname))
    -> FeatureMerger_8 [SUPPLIER]
FeatureMerger_8
    ATTR_ACCUM_MODE = Merge Supplier
    ATTR_CONFLICT_RES_LOOKUP = REQUESTOR_IF_CONFLICT
    IGNORE_NULLS = No
    JOIN_KEYS = @Value(Filnamn databas) @Value(path_rootname) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
