FME workspace update_protokoll2.fmw

Parameters:
- SourceDataset_OGCGEOPACKAGE = \\argos.storage.uu.se\MyFolder$\krima354\kicki_arbetsfiler\kulturparken_smaland\find_unr\data.gpkg   # GeoPackage File
- DestDataset_XLSXW = \\argos.storage.uu.se\MyFolder$\krima354\kicki_arbetsfiler\kulturparken_smaland\Projektprotokoll_lev1.xlsx   # Destination Microsoft Excel File
- SourceDataset_CSV2 = \\argos.storage.uu.se\MyFolder$\krima354\kicki_arbetsfiler\kulturparken_smaland\Länkar på rapporter med Intrasisprojekt2.txt   # Source CSV (Comma Separated Value) File(s)
- SourceDataset_XLSXR = \\argos.storage.uu.se\MyFolder$\krima354\kicki_arbetsfiler\kulturparken_smaland\Projektprotokoll_lev1.xlsx   # Source Microsoft Excel File(s)
- SourceDataset_OGCGEOPACKAGE_3 = \\argos.storage.uu.se\MyFolder$\krima354\kicki_arbetsfiler\kulturparken_smaland\fardiga\aggregated.gpkg   # GeoPackage File

Readers:
- OGCGEOPACKAGE_1: OGCGEOPACKAGE from $(SourceDataset_OGCGEOPACKAGE)
- CSV2_1: CSV2 from $(SourceDataset_CSV2)
- XLSXR_1: XLSXR from $(SourceDataset_XLSXR)
- OGCGEOPACKAGE_2: OGCGEOPACKAGE from $(SourceDataset_OGCGEOPACKAGE_3)

Writers:
- XLSXW_1: XLSXW to $(DestDataset_XLSXW)

project_information (reader OGCGEOPACKAGE_2)
    attributes: intrasis_name text, pk mediumint, SiteId text, Plats text, Lst Dnr text, Raä Dnr text, Inventarienummer text, Projektkod text, Projektnamn text, Projektledare text, Uppdragsgivare text, Exploateringstyp text, Undersökningstyp text, Slutdatum text, Beskrivning text, id int,PrimaryKey
    -> FeatureMerger_3 [REQUESTOR]
Sheet5 (reader XLSXR_1)
    attributes: Filnamn databas char(43), Kommentar geopackage char(101), SM-intrasis projekt char(59), SM rapport char(36), Rapport länk char(215), Uppdragsnummer char(36), Uppdragnummmer_updated / kommentar char(66), Uppgett koordinatsystem number(4,0), Faktiskt koordinatsystem number(4,0), Sweref klart char(1), Koordinatsystem/geolokalisering kommentar char(1), Manuellt rektifierad char(1), Rektifiering precision char(1), Rektifiering kommentar char(1), Sekretesskontroll godkänd char(1), Klar för AGES char(1), Publicerad på AGES char(1)
    -> FeatureMerger_3 [SUPPLIER]
FeatureMerger_3
    ATTR_ACCUM_MODE = Merge Supplier
    ATTR_CONFLICT_RES_LOOKUP = REQUESTOR_IF_CONFLICT
    IGNORE_NULLS = No
    JOIN_KEYS = @Value(intrasis_name) @Value(Filnamn databas) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only

Bookmark: rapportlänk
CSV (reader CSV2_1) [off]
    attributes: intrasis varchar(44), beskr varchar(234), rapport varchar(298)
    -> AttributeEncoder_2 [off]
AttributeEncoder_2 [off]
    ATTRCHOICE_ACTION = SELECTED
    ATTRLIST = beskr intrasis rapport
    DEST_ENCODING = fme-system
    REPLACE_INVALID_CHARACTERS = Yes
    TREAT_AS_BYTES_LU = FALSE
    ATTRCHOICE = Selected Attributes
    TREAT_AS_BYTES = Honor Encoding
    -> AttributeManager_3 [off]
AttributeManager_3 [off]
    ATTR_TABLE = SET_TO intrasis (varchar(44)) = @ReplaceString(@LowerCase(@Value(intrasis)),:,,caseSensitive=TRUE)
    -> FeatureMerger_2 [REQUESTOR] [off]
Sheet4 (reader XLSXR_1) [off]
    attributes: Filnamn databas char(14), Kommentar geopackage char(101), SM-intrasis projekt char(59), SM rapport char(36), Rapport länk string, Uppdragsnummer char(36), Uppdragnummmer_updated / kommentar char(66), Uppgett koordinatsystem number(4,0), Faktiskt koordinatsystem number(4,0), Sweref klart string, Koordinatsystem/geolokalisering kommentar string, Manuellt rektifierad string, Rektifiering precision string, Rektifiering kommentar string, Sekretesskontroll godkänd string, Klar för AGES string, Publicerad på AGES string
    -> AttributeEncoder [off]
AttributeEncoder [off]
    ATTRCHOICE_ACTION = SELECTED
    ATTRLIST = Faktiskt koordinatsystem Filnamn databas Klar för AGES Kommentar geopackage Koordinatsystem/geolokalisering kommentar Manuellt rektifierad Publicerad på AGES Rapport länk Rektifiering kommentar Rektifiering precision Sekretesskontroll godkänd SM rapport SM-intrasis projekt Sweref klart Uppdragnummmer_updated / kommentar Uppdragsnummer Uppgett koordinatsystem
    DEST_ENCODING = fme-system
    REPLACE_INVALID_CHARACTERS = Yes
    TREAT_AS_BYTES_LU = FALSE
    ATTRCHOICE = Selected Attributes
    TREAT_AS_BYTES = Honor Encoding
    -> FeatureMerger_2 [SUPPLIER] [off]
FeatureMerger_2 [off]
    ATTR_ACCUM_MODE = Merge Supplier
    ATTR_CONFLICT_RES_LOOKUP = REQUESTOR_IF_CONFLICT
    IGNORE_NULLS = No
    JOIN_KEYS = @Value(intrasis) @Value(Filnamn databas) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> AttributeManager_4 [off]
    UNMERGED_REQUESTOR -> AttributeManager_5 [off]
    UNUSED_SUPPLIER -> Sheet5 (writer XLSXW_1) [off]
AttributeManager_4 [off]
    ATTR_TABLE = RENAME_SET_VALUE rapport > Rapport länk (varchar(298))
    -> Sheet5 (writer XLSXW_1) [off]
AttributeManager_5 [off]
    ATTR_TABLE:
      RENAME_SET_VALUE intrasis > Filnamn databas (varchar(44))
      SET_TO Faktiskt koordinatsystem (int16)
      SET_TO Klar för AGES (varchar(1))
      SET_TO Kommentar geopackage (varchar(101)) = Det finns en rapport men inget gpkg eller med i excellistan
      SET_TO Koordinatsystem/geolokalisering kommentar (varchar(1))
      SET_TO Manuellt rektifierad (varchar(1))
      SET_TO Publicerad på AGES (varchar(1))
      SET_TO Rapport länk (varchar(1))
      SET_TO Rektifiering kommentar (varchar(1))
      SET_TO Rektifiering precision (varchar(1))
      SET_TO Sekretesskontroll godkänd (varchar(1))
      SET_TO SM rapport (varchar(36))
      SET_TO SM-intrasis projekt (varchar(59))
      SET_TO Sweref klart (varchar(1))
      SET_TO Uppdragnummmer_updated / kommentar (varchar(66))
      SET_TO Uppdragsnummer (varchar(36))
      SET_TO Uppgett koordinatsystem (int16)
    -> Sheet5 (writer XLSXW_1) [off]
Sheet5 (writer XLSXW_1) [off]
    attributes: Filnamn databas string(14), Kommentar geopackage string(101), SM-intrasis projekt string(59), SM rapport string(36), Rapport länk string(20), Uppdragsnummer string(20), Uppdragnummmer_updated / kommentar string(20), Uppgett koordinatsystem number(4), Faktiskt koordinatsystem number(4), Sweref klart string(1), Koordinatsystem/geolokalisering kommentar string(1), Manuellt rektifierad string(1), Rektifiering precision string(1), Rektifiering kommentar string(1), Sekretesskontroll godkänd string(1), Klar för AGES string(1), Publicerad på AGES string(1)

Bookmark: uuid-update
project_info_koll (reader OGCGEOPACKAGE_1) [off]
    attributes: intrasis_name text, intrasis text(44), beskr text(264), rapport text(298), pk mediumint, siteid text, plats text, lst dnr text, raä dnr text, inventarienummer text, projektkod text, projektnamn text, projektledare text, uppdragsgivare text, exploateringstyp text, undersökningstyp text, slutdatum text, beskrivning text, _part_number text(20), _geometry_label text, id int,PrimaryKey
    -> FeatureMerger [SUPPLIER] [off]
Sheet2 (reader XLSXR_1) [off]
    attributes: Filnamn databas char(14), Kommentar geopackage char(101), SM-intrasis projekt char(59), SM rapport char(36), Uppdragsnummer string, Uppdragnummmer_updated / kommentar string, Uppgett koordinatsystem number(4,0), Faktiskt koordinatsystem number(4,0), Sweref klart string, Koordinatsystem/geolokalisering kommentar string, Manuellt rektifierad string, Rektifiering precision string, Rektifiering kommentar string, Sekretesskontroll godkänd string, Klar för AGES string, Publicerad på AGES string
    -> FeatureMerger [REQUESTOR]
FeatureMerger [off]
    ATTR_ACCUM_MODE = Merge Supplier
    ATTR_CONFLICT_RES_LOOKUP = REQUESTOR_IF_CONFLICT
    IGNORE_NULLS = No
    JOIN_KEYS = @Value(Filnamn databas) @Value(intrasis_name) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> Tester [off]
    UNMERGED_REQUESTOR -> Sheet4 (writer XLSXW_1) [off]
Tester [off]
    BOOL_OP = OR
    TEST_CLAUSE = TEST @Value(siteid) = hittas ej
    TEST_MODE = TEST
    PASSED -> AttributeManager [off]
    FAILED -> AttributeManager_2 [off]
AttributeManager [off]
    ATTR_TABLE:
      SET_TO Uppdragnummmer_updated / kommentar (varchar(1)) = @Value(siteid)-@Value(plats)
      SET_TO beskr (varchar(264))
    -> Sheet4 (writer XLSXW_1) [off]
AttributeManager_2 [off]
    ATTR_TABLE:
      SET_TO Uppdragsnummer (buffer) = @Value(siteid)
      SET_TO Uppdragnummmer_updated / kommentar (buffer) = @Value(plats)
    -> Sheet4 (writer XLSXW_1) [off]
Sheet4 (writer XLSXW_1) [off]
    attributes: Filnamn databas string(14), Kommentar geopackage string(101), SM-intrasis projekt string(59), SM rapport string(36), Rapport länk string(20), Uppdragsnummer string(20), Uppdragnummmer_updated / kommentar string(20), Uppgett koordinatsystem number(4), Faktiskt koordinatsystem number(4), Sweref klart string(1), Koordinatsystem/geolokalisering kommentar string(1), Manuellt rektifierad string(1), Rektifiering precision string(1), Rektifiering kommentar string(1), Sekretesskontroll godkänd string(1), Klar för AGES string(1), Publicerad på AGES string(1)
