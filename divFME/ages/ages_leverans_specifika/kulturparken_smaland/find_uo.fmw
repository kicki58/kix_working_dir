FME workspace find_uo.fmw

Parameters:
- SourceDataset_OGCGEOPACKAGE = C:\ny_slask\GIS-data\arkeologiska_uppdrag_undersökningsområden_sverige (9).gpkg   # GeoPackage File
- SourceDataset_OGCGEOPACKAGE_3 = \\argos.storage.uu.se\MyFolder$\krima354\kicki_arbetsfiler\kulturparken_smaland\fardiga\aggregated.gpkg   # GeoPackage File
- SourceDataset_CSV2 = \\argos.storage.uu.se\MyFolder$\krima354\kicki_arbetsfiler\kulturparken_smaland\Länkar på rapporter med Intrasisprojekt2.txt   # Source CSV (Comma Separated Value) File(s)
- DestDataset_OGCGEOPACKAGE = \\argos.storage.uu.se\MyFolder$\krima354\kicki_arbetsfiler\kulturparken_smaland\find_unr\data.gpkg   # GeoPackage File

Readers:
- OGCGEOPACKAGE_1: OGCGEOPACKAGE from $(SourceDataset_OGCGEOPACKAGE)
- OGCGEOPACKAGE_2: OGCGEOPACKAGE from $(SourceDataset_OGCGEOPACKAGE_3)
- CSV2_1: CSV2 from $(SourceDataset_CSV2)

Writers:
- OGCGEOPACKAGE_3: OGCGEOPACKAGE to $(DestDataset_OGCGEOPACKAGE)

CSV (reader CSV2_1)
    attributes: intrasis varchar(44), beskr varchar(264), rapport varchar(298)
    -> AttributeManager
AttributeManager
    ATTR_TABLE = SET_TO intrasis (varchar(44)) = @LowerCase(@ReplaceString(@Value(intrasis),:,,caseSensitive=TRUE))
    -> FeatureMerger [REQUESTOR]
arkeologiska_uppdrag_undersökningsområden_sverige_linestring (reader OGCGEOPACKAGE_1)
    attributes: id text(255), uppdragsnummer text(9), beslutande_myndighet text(255), beslutsdatum date, diarienummer text(255), uppdragstyp text(255), utforande_organisation text(255), nollresultat text(9), url text(255), status text(255), lan text, kommun text, socken text, fid int,PrimaryKey
    -> Tester
arkeologiska_uppdrag_undersökningsområden_sverige_point (reader OGCGEOPACKAGE_1)
    attributes: id text(255), uppdragsnummer text(9), beslutande_myndighet text(255), beslutsdatum date, diarienummer text(255), uppdragstyp text(255), utforande_organisation text(255), nollresultat text(9), url text(255), status text(255), lan text, kommun text, socken text, fid int,PrimaryKey
    -> Bufferer
Bufferer
    ANGLE = 22.5
    CAP_STYLE_LOOKUP = CAP_ARC
    CORNER_STYLE_LOOKUP = JOIN_ARC
    MODE = AREA
    OFFSET = 2000
    OFFSET_UNITS = METERS
    PRECISION = APPROX
    CAP_STYLE = Arc
    CORNER_STYLE = Arc
    BUFFERED -> Tester
arkeologiska_uppdrag_undersökningsområden_sverige_polygon (reader OGCGEOPACKAGE_1)
    attributes: id text(255), uppdragsnummer text(9), beslutande_myndighet text(255), beslutsdatum date, diarienummer text(255), uppdragstyp text(255), utforande_organisation text(255), nollresultat text(9), url text(255), status text(255), lan text, kommun text, socken text, fid int,PrimaryKey
    -> Tester
Tester
    BOOL_OP = OR
    TEST_CLAUSE:
      TEST @Value(utforande_organisation) = Kulturparken Småland
      TEST @Value(utforande_organisation) = Kulturparken Småland AB
    TEST_MODE = TEST
    PASSED -> SpatialFilter [Filter]
features (reader OGCGEOPACKAGE_2)
    attributes: intrasis_name text, object_id mediumint, Class text, SubClass text, SymbolId mediumint, GeoObjectId mediumint, spatial_type text, id int,PrimaryKey
    -> Aggregator
Aggregator
    ACCUM_ATTRS = None
    AGGREGATE_TYPE = Homogeneous Collection (If Possible)
    GROUP_BY = intrasis_name
    MODE = Geometry - Assemble One Level
    SEP = ,
    AGGREGATE -> SpatialFilter [Candidate]
project_information (reader OGCGEOPACKAGE_2)
    attributes: intrasis_name text, pk mediumint, SiteId text, Plats text, Lst Dnr text, Raä Dnr text, Inventarienummer text, Projektkod text, Projektnamn text, Projektledare text, Uppdragsgivare text, Exploateringstyp text, Undersökningstyp text, Slutdatum text, Beskrivning text, id int,PrimaryKey
    -> FeatureMerger [SUPPLIER]
FeatureMerger
    ATTR_ACCUM_MODE = Merge Supplier
    ATTR_CONFLICT_RES_LOOKUP = REQUESTOR_IF_CONFLICT
    IGNORE_NULLS = No
    JOIN_KEYS = @Value(intrasis) @Value(intrasis_name) AUTO
    MERGE_TYPE_VAL = GEOM_AND_ATTRS
    PROCESS_DUPS = NO
    REJECT_NULL_MISSING_KEYS = No
    SUPPLIERS_FIRST = No
    ATTR_CONFLICT_RES = Use Requestor
    MERGE_TYPE = Attributes and Geometry
    MERGED -> SpatialFilter [Candidate]
    MERGED -> project_info_koll (writer OGCGEOPACKAGE_3)
    UNMERGED_REQUESTOR -> i_rapport_utan_proj (writer OGCGEOPACKAGE_3)
    UNUSED_SUPPLIER -> SpatialFilter [Candidate]
SpatialFilter
    AGGREGATE_HANDLING = Yes
    ATTR_CONFLICT_RES_LOOKUP = CANDIDATE_IF_CONFLICT
    BOOL_OP = OR
    BOUNDING_BOX = NO
    CURVE_BOUNDARY_RULE = ENDPOINTS_MOD2
    MULTI_BASE = YES
    PREDATTR = _predicate
    PREDICATES = INTERSECTS WITHIN CONTAINS EQUALS TOUCHES
    ATTR_ACCUM_MODE = Merge Filter
    ATTR_CONFLICT_RES = Use Candidate
    BASE_TYPE = Multiple Filters
    CURVE_BOUNDARY_RULE_PARAM = Default Rule
    PASS_CRITERIA = Pass Against One Filter
    USE_BOUNDING_BOX = No
    PASSED -> Deaggregator
    FAILED -> Deaggregator_2
Deaggregator
    ATTR_ACCUM_MODE = HANDLE_CONFLICT
    ATTR_CONFLICT_RES = INCOMING_IF_CONFLICT
    EXPLODE_INSTANCES = No
    GEOM_LABEL_FIELD = _geometry_label
    LIST_ATTR_MODE_LOOKUP = LEAN
    PART_NUMBER_FIELD = _part_number
    RECURSIVE = No
    SPLIT_COMPOSITES = No
    DEAGGREGATED -> BulkAttributeRemover
BulkAttributeRemover
    ATTR_EXP = @Value(fid)
    -> found (writer OGCGEOPACKAGE_3)
found (writer OGCGEOPACKAGE_3)
    attributes: id text(255), uppdragsnummer text(9), beslutande_myndighet text(255), beslutsdatum date, diarienummer text(255), uppdragstyp text(255), utforande_organisation text(255), nollresultat text(9), url text(255), status text(255), lan text, kommun text, socken text, intrasis_name text, intrasis text(44), beskr text(264), rapport text(298), pk mediumint, siteid text, plats text, lst dnr text, raä dnr text, inventarienummer text, projektkod text, projektnamn text, projektledare text, uppdragsgivare text, exploateringstyp text, undersökningstyp text, slutdatum text,
      beskrivning text, _predicate text, _part_number text(20), _geometry_label text
Deaggregator_2
    ATTR_ACCUM_MODE = HANDLE_CONFLICT
    ATTR_CONFLICT_RES = INCOMING_IF_CONFLICT
    EXPLODE_INSTANCES = No
    GEOM_LABEL_FIELD = _geometry_label
    LIST_ATTR_MODE_LOOKUP = LEAN
    PART_NUMBER_FIELD = _part_number
    RECURSIVE = No
    SPLIT_COMPOSITES = No
    DEAGGREGATED -> not_found (writer OGCGEOPACKAGE_3)
not_found (writer OGCGEOPACKAGE_3)
    attributes: intrasis_name text, intrasis text(44), beskr text(264), rapport text(298), pk mediumint, siteid text, plats text, lst dnr text, raä dnr text, inventarienummer text, projektkod text, projektnamn text, projektledare text, uppdragsgivare text, exploateringstyp text, undersökningstyp text, slutdatum text, beskrivning text, id int, _part_number text(20), _geometry_label text
project_info_koll (writer OGCGEOPACKAGE_3)
    attributes: intrasis_name text, intrasis text(44), beskr text(264), rapport text(298), pk mediumint, siteid text, plats text, lst dnr text, raä dnr text, inventarienummer text, projektkod text, projektnamn text, projektledare text, uppdragsgivare text, exploateringstyp text, undersökningstyp text, slutdatum text, beskrivning text, id int,PrimaryKey, _part_number text(20), _geometry_label text
i_rapport_utan_proj (writer OGCGEOPACKAGE_3)
    attributes: intrasis text(44), beskr text(264), rapport text(298)
