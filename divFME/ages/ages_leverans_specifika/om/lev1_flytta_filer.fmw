FME workspace lev1_flytta_filer.fmw

Parameters:
- SourceDataset_PATH = C:\ny_slask\olm_working\ej_importerat   # INCLUDE_WEB_BROWSER Source Folder and File Pathnames Folder
- SourceDataset_XLSXR = Z:\3 - AGES\Östergötlands Länsmuseum\Leverans 1\2 - Bearbetning\Projektprotokoll_ÖM_lev1_21_mars.xlsx   # Source Microsoft Excel File(s)
- DestDataset_FILECOPY = C:\ny_slask\olm_working\ej_importerat\inget_uppdragsnr   # Destination File Copy Folder

Readers:
- PATH_1: PATH from $(SourceDataset_PATH)
- XLSXR_1: XLSXR from $(SourceDataset_XLSXR)

Writers:
- FILECOPY_1: FILECOPY to $(DestDataset_FILECOPY)

PATH (reader PATH_1)
    attributes: path_unix buffer, path_windows buffer, path_rootname buffer, path_filename buffer, path_extension buffer, path_directory_unix buffer, path_directory_windows buffer, path_type char(10)
    -> DuplicateFilter_2
DuplicateFilter_2
    INPUT_ORDERED_CHOICE_LOOKUP = NO
    KEYATTR = path_rootname
    INPUT_ORDERED_CHOICE = No
    UNIQUE -> AttributeManager
    UNIQUE -> FeatureMerger_4 [SUPPLIER]
    DUPLICATE -> BulkAttributeRenamer
AttributeManager
    ATTR_TABLE = RENAME_SET_VALUE path_windows > filecopy_source_dataset (buffer)
    -> FeatureMerger [SUPPLIER]
BulkAttributeRenamer
    ATTRCHOICE_ACTION = NONPROTECTEDFME
    MODE_CHOICE = RENAME
    PATTERN_ACTION_DISP = ADDPREFIX
    REPLACE_STR = dup
    ATTRCHOICE = All Attributes
    -> FeatureMerger_4 [REQUESTOR]
FeatureMerger_4
    ATTR_ACCUM_MODE = Merge Supplier
    ATTR_CONFLICT_RES_LOOKUP = REQUESTOR_IF_CONFLICT
    IGNORE_NULLS = No
    JOIN_KEYS = @Value(duppath_rootname) @Value(path_rootname) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
Sheet2 (reader XLSXR_1)
    attributes: Filnamn databas char(10), Kommentar geopackage char(61), Uppdragsnummer char(31), Rapport ref char(140), Uppdragnummmer_updated / kommentar char(32), Uppgett koordinatsystem number(4,0), Faktiskt koordinatsystem number(4,0), Sweref klart char(2), Manuellt rektifierad char(1), Rektifiering precision char(1), Rektifiering kommentar char(1), Sekretesskontroll kommentar char(51), Klar för AGES char(3), Publicerad på AGES char(2), Kommentar char(1)
    -> Tester
Note: ta bort tom rad från excel
Tester
    BOOL_OP = OR
    TEST_CLAUSE = TEST Filnamn databas ATTRIBUTE_HAS_A_VALUE ""
    TEST_MODE = TEST
    PASSED -> AttributeFilter_2
    PASSED -> DuplicateFilter
Note: ta bort redan publicerade
AttributeFilter_2
    ATTR_NAME = Publicerad på AGES
    ATTR_VALUES = <Empty>,<Missing>,<Null>,<Unfiltered>,FME_NULL_VALUE,JA
    <EMPTY> -> AttributeFilter
    <NULL> -> AttributeFilter
Note: klar för ages
AttributeFilter
    ATTR_NAME = Klar för AGES
    ATTR_VALUES = <Empty>,<Missing>,<Null>,<Unfiltered>,FME_NULL_VALUE,JA,NEJ
    JA -> FeatureMerger [REQUESTOR]
FeatureMerger
    ATTR_ACCUM_MODE = Merge Supplier
    ATTR_CONFLICT_RES_LOOKUP = REQUESTOR_IF_CONFLICT
    IGNORE_NULLS = No
    JOIN_KEYS = @Value(Filnamn databas) @Value(path_rootname) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> publicera (writer FILECOPY_1)
    UNUSED_SUPPLIER -> FeatureMerger_2 [REQUESTOR]
publicera (writer FILECOPY_1)
DuplicateFilter
    INPUT_ORDERED_CHOICE_LOOKUP = NO
    KEYATTR = Filnamn databas
    INPUT_ORDERED_CHOICE = No
    UNIQUE -> FeatureMerger_2 [SUPPLIER]
FeatureMerger_2
    ATTR_ACCUM_MODE = Merge Supplier
    ATTR_CONFLICT_RES_LOOKUP = REQUESTOR_IF_CONFLICT
    IGNORE_NULLS = No
    JOIN_KEYS = @Value(path_rootname) @Value(Filnamn databas) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> AttributeFilter_3
AttributeFilter_3
    ATTR_NAME = Kommentar geopackage
    ATTR_VALUES = <Empty>,<Missing>,<Null>,<Unfiltered>,FME_NULL_VALUE,Ej rapporterad ännu, publicera ej.,gpkg saknas i excel från olm- vet ej status på intrasisproj,Verkar ej vara rapporterad.
    <NULL> -> inget_uppdragsnummer (writer FILECOPY_1)
    <UNFILTERED> -> säkerhetsproblem (writer FILECOPY_1)
    Ej rapporterad ännu, publicera ej. -> status_oklar (writer FILECOPY_1)
    Verkar ej vara rapporterad. -> status_oklar (writer FILECOPY_1)
inget_uppdragsnummer (writer FILECOPY_1)
säkerhetsproblem (writer FILECOPY_1)
status_oklar (writer FILECOPY_1)
