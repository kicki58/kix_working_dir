FME workspace save2gpkg_utanID.fmw
Startup Python:
      import fmeobjects

Parameters:
- db_name = 2361_Ängsliljan_SU   # db namn
- DestDataset_OGCGEOPACKAGE = C:\Github\kix\SiteWorks-Py\$(db_name).gpkg   # GeoPackage File
- SourceDataset_PATH = C:\Github\kix\SiteWorks-Py\result_csv   # INCLUDE_WEB_BROWSER Source Folder and File Pathnames Folder
- SourceDataset_CSV2_43 = C:\Github\kix\SiteWorks-Py\result_csv\2361_Ängsliljan_SU\csv\OBJDATA.csv   # Source CSV OBJDATA
- SourceDataset_CSV2_59 = C:\Github\kix\SiteWorks-Py\result_csv\2361_Ängsliljan_SU\csv\OBJ.csv   # Source CSV OBJ
- SourceDataset_CSV2_63 = C:\Github\kix\SiteWorks-Py\result_csv\2361_Ängsliljan_SU\csv\OBJDETAILS.csv   # Source CSV OBJDETAILS
- SourceDataset_CSV2_46 = C:\Github\kix\SiteWorks-Py\result_csv\2361_Ängsliljan_SU\csv\PROJECT.csv   # Source CSV PROJECT
- SourceDataset_XLSXR = $(FME_MF_DIR)metadatamallen_sw.xlsx   # Source Microsoft Excel File(s)
- SourceDataset_CSV2 = C:\Github\kix\SiteWorks-Py\result_csv\2361_Ängsliljan_SU\csv\RELATIONS.csv   # Source CSV RELATIONS

Readers:
- CSV2_16: CSV2 from $(SourceDataset_CSV2_59)
- CSV2_17: CSV2 from $(SourceDataset_CSV2_63)
- CSV2_24: CSV2 from $(SourceDataset_CSV2_46)
- CSV2_12: CSV2 from $(SourceDataset_CSV2_43)
- PATH_1: PATH from $(SourceDataset_PATH)
- XLSXR_1: XLSXR from $(SourceDataset_XLSXR)
- CSV2_1: CSV2 from $(SourceDataset_CSV2)

Writers:
- OGCGEOPACKAGE_1: OGCGEOPACKAGE to $(DestDataset_OGCGEOPACKAGE)
- SQLITE3_2: SQLITE3 to $(DestDataset_OGCGEOPACKAGE)

Note: CSV: RELATIONS
Note: Det går inte att använda related_table eftersom id'en är dubbla (objecno + subobject) och är inte unika....
CSV (reader CSV2_1)
    attributes: PROJECT uint32, CATEGORY varchar(12), OBJECTNO uint32, SUBOBJECT uint32, RTYPE uint32, COBJECTNO uint32, CSUBOBJECT uint32
    -> Counter
    -> relations (writer SQLITE3_2)
relations (writer SQLITE3_2)
    attributes: PROJECT integer, CATEGORY varchar(12), OBJECTNO integer, SUBOBJECT integer, RTYPE integer, COBJECTNO integer, CSUBOBJECT integer

Bookmark: fixfix geom
Note: CSV: OBJDATA [CSV2] / geometrier
CSV (reader CSV2_12)
    attributes: SEQNO uint32, X x_coordinate, Y y_coordinate, Z z_coordinate, OBJECTID uint32
    -> VertexCreator
VertexCreator
    MEASURE_TYPE_LOOKUP = CONTINUOUS
    MODE = REPLACE
    REMOVE_ATTRIBUTES = No
    XVAL = @Value(X)
    YVAL = @Value(Y)
    ZVAL = @Value(Z)
    MEASURE_TYPE = Continuous
    MODE_NAME = Replace with Point
    -> Sorter
    -> Aggregator
LineBuilder_2
    ACCUM_INPUT_ATTRS_LOOKUP = One
    GROUP_BY = OBJECTID
    REMOVE_DUPLICATES_LOOKUP = NO
    ACCUM_INPUT_ATTRS = Use Attributes From One Feature
    REMOVE_DUPLICATES = No
    POINT -> FeatureMerger_2 [REQUESTOR]
    LINE -> FeatureMerger_2 [REQUESTOR]
    POLYGON -> FeatureMerger_2 [REQUESTOR]
Note: CSV: OBJ [CSV2]
CSV (reader CSV2_16)
    attributes: PROJECT uint32, CATEGORY varchar(12), OBJECTNO uint32, SUBOBJECT uint32, TYPENO uint32, DESCRIPTION varchar(1), SUBCLASS varchar(1), DEFINITION varchar(1), INTERPRETATIONS varchar(192), X_AVG x_coordinate, Y_AVG y_coordinate, Z_AVG z_coordinate, OBJLENGTH varchar(1), WIDTH varchar(1), NUMBEROF uint32, WEIGHT varchar(1), BELONGSTO uint32, BELONGSTOSUB uint32, BELONGSTOTYPE varchar(8), CONTEXT varchar(1), CONTEXTOBJECT varchar(1), CONTEXTSUBOBJECT varchar(1), CONTEXTTYPE varchar(1), INCLINATION varchar(1), DATEOFRECORDING datetime, MPRECISION varchar(1), SIGN varchar(33), DATING varchar(1), DATING_MARGINOFERROR varchar(1), DATINGMETHOD varchar(1),
      NONMEASUREDLOCATION varchar(1), MEASUREMENTFILE varchar(16), STRUCKOFF varchar(2), CONSTRUCTION uint32, SUBCONSTRUCTION uint32, ORIENTATION varchar(1), FORM varchar(1), COURNERS varchar(1), HEIGHT varchar(1), RIM varchar(1), BOTTOMRIM varchar(1), BOTTOM varchar(1), SECTION varchar(1), CONDITION varchar(1), SPLITTING varchar(1), TOOLTRACES varchar(1), ASSEMBLY varchar(1), MATERIAL varchar(1), GRANULARITY varchar(1), SURFACE varchar(1), JOINTINGMATERIAL varchar(1), SORTING varchar(1), STRUCTURE varchar(1), CONTENTS varchar(1), CONSISTENCE varchar(1), PACKING varchar(1), COLOUR varchar(1), COMPOSITION varchar(1), JOINTING varchar(1), CHALK varchar(1),
      COAL varchar(1), PEBBELS varchar(1), BRICKFRAG varchar(1), BRICK varchar(1), WOOD varchar(1), CLAY varchar(1), BURNT_CLAY varchar(1), DAUB varchar(1), GRAVEL varchar(1), SOOT varchar(1), ASHES varchar(1), ANIMALBONES varchar(1), FISHBONES varchar(1), ROCKS varchar(1), HUMUS varchar(1), BURNT_BONE varchar(1), UNBURNT_BONE varchar(1), FIRE_CRACKED_ROCK varchar(1), BURNT_STONE varchar(1), MACHINE varchar(1), SHOVEL varchar(1), HOETABLE varchar(1), TROWEL varchar(1), SIEVE varchar(1), PREPARATION varchar(1), CONTAMINATION varchar(1), DROUGHT varchar(1), RAIN varchar(1), FROST varchar(1), WATERSIEVE varchar(1),
      RECORDEDBY varchar(1), VERIFIED varchar(1), OBSERVATIONS varchar(4), CONTACT_ABOVE varchar(1), CONTACT_BELOW varchar(1), SIDE varchar(1), LIMITS varchar(1), MAXHEIGHT varchar(1), DETAILS varchar(1), TAQ varchar(1), TPQ varchar(1), STRATATOP varchar(1), STRATABOTTOM varchar(1), SAND varchar(1), LIME varchar(1), PREV_FUNCTION varchar(1), DATEEDITED datetime, BLAZINGCOLOR varchar(1), FILLING varchar(1), TIERS varchar(1), TIER_DEPTH varchar(1), OBJECTID uint32, BELONGSTOID uint32, CONST_PHASE varchar(1), DEST_PHASE varchar(1), AREA real64, SILT varchar(1), ORGANIC_MATTER varchar(1), BOULDERS varchar(1), NOTES varchar(4),
      IDX uint32, TYPENAME varchar(22), CLASS varchar(11), CONT_CLASS varchar(1), DIAMETER varchar(1), PART varchar(1), INNER_LENGTH varchar(1), INNER_WIDTH varchar(1), INNER_HEIGHT varchar(1), SECTIONS varchar(1), EXAMINATION varchar(1), THICKNESS varchar(1), FRAGMENTS varchar(1)
    -> AttributeManager_6
AttributeManager_6
    -> AttributeKeeper
    -> objects (writer SQLITE3_2)
    -> FeatureMerger_5 [REQUESTOR]
AttributeKeeper
    CREATE_BULK_MODE_FEATURES = NO
    KEEP_ATTRS = OBJECTID,OBJECTNO,TYPENO,CLASS,SUBOBJECT
    -> FeatureMerger_2 [SUPPLIER]
FeatureMerger_2
    ATTR_ACCUM_MODE = Merge Supplier
    ATTR_CONFLICT_RES_LOOKUP = REQUESTOR_IF_CONFLICT
    IGNORE_NULLS = No
    JOIN_KEYS = @Value(OBJECTID) @Value(OBJECTID) AUTO
    MERGE_TYPE_VAL = ATTRIBUTES
    PRESERVE_FEATURE_ORDER_LOOKUP = PER_OUTPUT_PORT
    PROCESS_DUPS = NO
    REJECT_NULL_MISSING_KEYS = No
    SUPPLIERS_FIRST = No
    ATTR_CONFLICT_RES = Use Requestor
    MERGE_TYPE = Attributes Only
    MERGED -> TestFilter_2
TestFilter_2
    DEFAULT_VALUE = <UNFILTERED>
    PASSED_TEST_GROUP_OUTPUT = FIRST
    TEST_LIST = "BOOL_OP,OR,COMPOSITE_TEST,""""""1"""""",TEST_CLAUSE,TEST TYPENO ATTRIBUTE_HAS_A_VALUE """,TYPENO ATTRIBUTE_HAS_A_VALUE
    TYPENO ATTRIBUTE_HAS_A_VALUE -> FeatureMerger_3 [REQUESTOR]
objects (writer SQLITE3_2)
    attributes: DATEOFRECORDING text, DATEEDITED text, X_AVG double, Y_AVG double, Z_AVG double, AREA double, PROJECT integer, OBJECTNO integer, SUBOBJECT integer, TYPENO integer, NUMBEROF integer, BELONGSTO integer, BELONGSTOSUB integer, CONSTRUCTION integer, SUBCONSTRUCTION integer, OBJECTID integer, BELONGSTOID integer, IDX integer, BOULDERS text, NOTES text, TYPENAME text, CLASS text, CONT_CLASS text, DIAMETER text, PART text, INNER_LENGTH text, INNER_WIDTH text, INNER_HEIGHT text, SECTIONS text, EXAMINATION text,
      THICKNESS text, FRAGMENTS text, CATEGORY text, DESCRIPTION text, SUBCLASS text, DEFINITION text, INTERPRETATIONS text, OBJLENGTH text, WIDTH text, WEIGHT text, BELONGSTOTYPE text, CONTEXT text, CONTEXTOBJECT text, CONTEXTSUBOBJECT text, CONTEXTTYPE text, INCLINATION text, MPRECISION text, SIGN text, DATING text, DATING_MARGINOFERROR text, DATINGMETHOD text, NONMEASUREDLOCATION text, MEASUREMENTFILE text, STRUCKOFF text, ORIENTATION text, FORM text, COURNERS text, HEIGHT text, RIM text, BOTTOMRIM text,
      BOTTOM text, SECTION text, CONDITION text, SPLITTING text, TOOLTRACES text, ASSEMBLY text, MATERIAL text, GRANULARITY text, SURFACE text, JOINTINGMATERIAL text, SORTING text, STRUCTURE text, CONTENTS text, CONSISTENCE text, PACKING text, COLOUR text, COMPOSITION text, JOINTING text, CHALK text, COAL text, PEBBELS text, BRICKFRAG text, BRICK text, WOOD text, CLAY text, BURNT_CLAY text, DAUB text, GRAVEL text, SOOT text, ASHES text,
      ANIMALBONES text, FISHBONES text, ROCKS text, HUMUS text, BURNT_BONE text, UNBURNT_BONE text, FIRE_CRACKED_ROCK text, BURNT_STONE text, MACHINE text, SHOVEL text, HOETABLE text, TROWEL text, SIEVE text, PREPARATION text, CONTAMINATION text, DROUGHT text, RAIN text, FROST text, WATERSIEVE text, RECORDEDBY text, VERIFIED text, OBSERVATIONS text, CONTACT_ABOVE text, CONTACT_BELOW text, SIDE text, LIMITS text, MAXHEIGHT text, DETAILS text, TAQ text, TPQ text,
      STRATATOP text, STRATABOTTOM text, SAND text, LIME text, PREV_FUNCTION text, BLAZINGCOLOR text, FILLING text, TIERS text, TIER_DEPTH text, CONST_PHASE text, DEST_PHASE text, SILT text, ORGANIC_MATTER text
Note: CSV: OBJDETAILS [CSV2]
CSV (reader CSV2_17)
    attributes: PROJECT string, CATEGORY string, OBJECTNO string, SUBOBJECT string, COLOUR string, TECHNIQUE string, WEARMARKS string, PROCESSES string, DECORATION string, SHAPE string, S1 string, S2 string, S3 string, S4 string, S5 string, S6 string, OBJECTID string, IDX string
    -> AttributeManager_7
AttributeManager_7
    -> object_details (writer SQLITE3_2)
object_details (writer SQLITE3_2)
    attributes: PROJECT text, CATEGORY text, OBJECTNO text, SUBOBJECT text, COLOUR text, TECHNIQUE text, WEARMARKS text, PROCESSES text, DECORATION text, SHAPE text, S1 text, S2 text, S3 text, S4 text, S5 text, S6 text, OBJECTID text, IDX text
hela metadatamallen export (reader XLSXR_1)
    attributes: Version number(2,0), FieldName char(17), DisplayLabel char(20), FieldType char(8), FieldClass char(7), TYPENR number(4,0), MAP char(10), CATEGORYCODE char(3), CATEGORY char(12), CLASS char(28), TYPENAME char(28), CODE char(3), geometri char(8), ELEMENT_TYPE number(2,0), CONT_CLASS string, SYMBOLSIZE number(4,0), SYMBOLTYPE number(2,0), MODULE string, isactproj string, LEVELNO number(2,0), VIEWTYPE number(2,0), ASCKONF number(2,0), COLOR number(2,0), WEIGHT number(2,0), STYLE number(2,0), FILL number(2,0), CLOSED number(2,0), PATTERN_TYPE number(3,0), PATTERN_CELLNAME char(5), ANGLE number(2,0),
      DIST number(2,0), XANGLE number(2,0), XDIST number(2,0), SCALE_PATTERN number(2,0), TEXT number(2,0), TEXT_LEVEL number(2,0), TEXT_SIZE number(3,1), TEXT_FONT number(3,0), TAG number(2,0), PLACECELLROTATE number(2,0), PLACECELLSCALE number(2,0), S1 char(16), S2 char(12), S3 char(5), S4 char(7), S5 char(6), S6 string, S7 string, S8 string, S9 string, S10 string
    -> AttributeKeeper_2
AttributeKeeper_2
    CREATE_BULK_MODE_FEATURES = NO
    KEEP_ATTRS = TYPENR,geometri,TYPENAME
    -> TestFilter_3
TestFilter_3
    DEFAULT_VALUE = <UNFILTERED>
    PASSED_TEST_GROUP_OUTPUT = FIRST
    TEST_LIST = "BOOL_OP,OR,COMPOSITE_TEST,""""""1"""""",TEST_CLAUSE,TEST TYPENAME ATTRIBUTE_HAS_A_VALUE """,TYPENAME ATTRIBUTE_HAS_A_VALUE
    TYPENAME ATTRIBUTE_HAS_A_VALUE -> FeatureMerger_3 [SUPPLIER]
FeatureMerger_3
    ATTR_ACCUM_MODE = Merge Supplier
    ATTR_CONFLICT_RES_LOOKUP = REQUESTOR_IF_CONFLICT
    IGNORE_NULLS = No
    JOIN_KEYS = @Value(TYPENO) @Value(TYPENR) AUTO
    MERGE_TYPE_VAL = ATTRIBUTES
    PRESERVE_FEATURE_ORDER_LOOKUP = PER_OUTPUT_PORT
    PROCESS_DUPS = NO
    REJECT_NULL_MISSING_KEYS = No
    SUPPLIERS_FIRST = No
    ATTR_CONFLICT_RES = Use Requestor
    MERGE_TYPE = Attributes Only
    MERGED -> AttributeFilter
AttributeFilter
    ATTR_NAME = geometri
    ATTR_VALUES = <Empty>,<Missing>,<Null>,<Unfiltered>,linje?,polygon,punkt,punkt?,linje
    PRESERVE_FEATURE_ORDER_LOOKUP = PER_OUTPUT_PORT
    linje? -> AttributeManager_5
    polygon -> LineCloser
    punkt -> AttributeManager_5
    punkt? -> AttributeManager_5
    linje -> AttributeManager_5
LineCloser
    CONNECT_Z_MODE_LOOKUP = FIRST_WINS
    CONNECT_Z_MODE = First Wins
    AREA -> AttributeManager_5
AttributeManager_5
    ATTR_TABLE:
      REMOVE SEQNO
      REMOVE X
      REMOVE Y
      REMOVE Z
      REMOVE TYPENO
      REMOVE TYPENR
    -> features (writer OGCGEOPACKAGE_1)
    -> FeatureMerger_5 [SUPPLIER]
features (writer OGCGEOPACKAGE_1)
    attributes: OBJECTID int, OBJECTNO int, CLASS text, geometri text, SUBOBJECT int, TYPENAME text
FeatureMerger_5 [off]
    ATTR_ACCUM_MODE = Merge Supplier
    ATTR_CONFLICT_RES_LOOKUP = REQUESTOR_IF_CONFLICT
    IGNORE_NULLS = No
    JOIN_KEYS = @Value(OBJCTNO_SUBOBJECT) @Value(OBJCTNO_SUBOBJECT) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> features00 (writer OGCGEOPACKAGE_1)
features00 (writer OGCGEOPACKAGE_1) [off]
    attributes: PROJECT int, CATEGORY text(12), OBJECTNO int, SUBOBJECT int, TYPENO int, DESCRIPTION text(1), SUBCLASS text(1), DEFINITION text(1), INTERPRETATIONS text(192), X_AVG double, Y_AVG double, Z_AVG double, OBJLENGTH text(1), WIDTH text(1), NUMBEROF int, WEIGHT text(1), BELONGSTO int, BELONGSTOSUB int, BELONGSTOTYPE text(8), CONTEXT text(1), CONTEXTOBJECT text(1), CONTEXTSUBOBJECT text(1), CONTEXTTYPE text(1), INCLINATION text(1), DATEOFRECORDING datetime, MPRECISION text(1), SIGN text(33), DATING text(1), DATING_MARGINOFERROR text(1), DATINGMETHOD text(1),
      NONMEASUREDLOCATION text(1), MEASUREMENTFILE text(16), STRUCKOFF text(2), CONSTRUCTION int, SUBCONSTRUCTION int, ORIENTATION text(1), FORM text(1), COURNERS text(1), HEIGHT text(1), RIM text(1), BOTTOMRIM text(1), BOTTOM text(1), SECTION text(1), CONDITION text(1), SPLITTING text(1), TOOLTRACES text(1), ASSEMBLY text(1), MATERIAL text(1), GRANULARITY text(1), SURFACE text(1), JOINTINGMATERIAL text(1), SORTING text(1), STRUCTURE text(1), CONTENTS text(1), CONSISTENCE text(1), PACKING text(1), COLOUR text(1), COMPOSITION text(1), JOINTING text(1), CHALK text(1),
      COAL text(1), PEBBELS text(1), BRICKFRAG text(1), BRICK text(1), WOOD text(1), CLAY text(1), BURNT_CLAY text(1), DAUB text(1), GRAVEL text(1), SOOT text(1), ASHES text(1), ANIMALBONES text(1), FISHBONES text(1), ROCKS text(1), HUMUS text(1), BURNT_BONE text(1), UNBURNT_BONE text(1), FIRE_CRACKED_ROCK text(1), BURNT_STONE text(1), MACHINE text(1), SHOVEL text(1), HOETABLE text(1), TROWEL text(1), SIEVE text(1), PREPARATION text(1), CONTAMINATION text(1), DROUGHT text(1), RAIN text(1), FROST text(1), WATERSIEVE text(1),
      RECORDEDBY text(1), VERIFIED text(1), OBSERVATIONS text(4), CONTACT_ABOVE text(1), CONTACT_BELOW text(1), SIDE text(1), LIMITS text(1), MAXHEIGHT text(1), DETAILS text(1), TAQ text(1), TPQ text(1), STRATATOP text(1), STRATABOTTOM text(1), SAND text(1), LIME text(1), PREV_FUNCTION text(1), DATEEDITED datetime, BLAZINGCOLOR text(1), FILLING text(1), TIERS text(1), TIER_DEPTH text(1), OBJECTID int, BELONGSTOID int, CONST_PHASE text(1), DEST_PHASE text(1), AREA double, SILT text(1), ORGANIC_MATTER text(1), BOULDERS text(1), NOTES text(4),
      IDX int, TYPENAME text(22), CLASS text(11), CONT_CLASS text(1), DIAMETER text(1), PART text(1), INNER_LENGTH text(1), INNER_WIDTH text(1), INNER_HEIGHT text(1), SECTIONS text(1), EXAMINATION text(1), THICKNESS text(1), FRAGMENTS text(1), geometri text(8)

Bookmark: project_information
Aggregator
    ACCUM_ATTRS = None
    AGGREGATE_TYPE = Heterogeneous Collection
    MODE = Geometry - Assemble One Level
    SEP = ,
    ACCUM_ATTRS_NAME = Drop Incoming Attributes
    AGGREGATE -> CenterPointExtractor
CenterPointExtractor
    CENTX = _inside_x
    CENTY = _inside_y
    CENTZ = _inside_z
    EXTRACTIONMODE = CENTEROFGRAV
    -> VertexCreator_2
VertexCreator_2
    MEASURE_TYPE_LOOKUP = CONTINUOUS
    MODE = REPLACE
    REMOVE_ATTRIBUTES = No
    XVAL = @Value(_inside_x)
    YVAL = @Value(_inside_y)
    ZVAL = @Value(_inside_z)
    MEASURE_TYPE = Continuous
    MODE_NAME = Replace with Point
    -> FeatureMerger_4 [SUPPLIER]
Sorter
    GROUP_BY = OBJECTID
    SORT_PARM = SEQNO NATURAL ASCENDING
    SORTED -> LineBuilder_2
Note: CSV: PROJECT [CSV2]
CSV (reader CSV2_24)
    attributes: PROJECT uint32, OFFICALDESIGNATION varchar(1), PROJECTNAME varchar(1), CLIENT varchar(1), PREMISES varchar(1), PARISH varchar(1), MONUMENT varchar(1), MUNICIPALITY varchar(1), COUNTY varchar(1), PROVINCE varchar(1), BASEMAP varchar(1), PROJECTMANAGER varchar(1), PARTICIPANTS varchar(1), TYPEOFPROJECT varchar(18), STARTOFPROJECT varchar(1), ENDOFPROJECT varchar(1), MANHOURS varchar(1), MACHINEHOURS varchar(1), AREAOFINVEST varchar(1), COORDINATESYST varchar(12), HEIGHTSYST varchar(1), MASL varchar(1), R1 uint32, R2 uint32, R3 uint32, R4 uint32, R5 uint32, R6 uint32, R7 uint32, R8 uint32,
      R9 uint32, R10 varchar(1), DOCMETHOD uint32, STATE uint32, EASTING_MAX x_coordinate, EASTING_MIN real32, NORTHING_MIN y_coordinate, NORTHING_MAX real64, R13 varchar(1)
    -> FeatureMerger_4 [REQUESTOR]
FeatureMerger_4
    ATTR_ACCUM_MODE = Merge Supplier
    ATTR_CONFLICT_RES_LOOKUP = REQUESTOR_IF_CONFLICT
    IGNORE_NULLS = No
    JOIN_KEYS = 1 1 AUTO
    MERGE_TYPE_VAL = GEOM_AND_ATTRS
    PRESERVE_FEATURE_ORDER_LOOKUP = PER_OUTPUT_PORT
    PROCESS_DUPS = NO
    REJECT_NULL_MISSING_KEYS = No
    SUPPLIERS_FIRST = No
    ATTR_CONFLICT_RES = Use Requestor
    MERGE_TYPE = Attributes and Geometry
    MERGED -> project_information (writer OGCGEOPACKAGE_1)
project_information (writer OGCGEOPACKAGE_1)
    attributes: EASTING_MAX double, NORTHING_MIN double, NORTHING_MAX double, EASTING_MIN float, PROJECT int, R1 int, R2 int, R3 int, R4 int, R5 int, R6 int, R7 int, R8 int, R9 int, DOCMETHOD int, STATE int, OFFICALDESIGNATION text, PROJECTNAME text, CLIENT text, PREMISES text, PARISH text, MONUMENT text, MUNICIPALITY text, COUNTY text, PROVINCE text, BASEMAP text, PROJECTMANAGER text, PARTICIPANTS text, TYPEOFPROJECT text, STARTOFPROJECT text,
      ENDOFPROJECT text, MANHOURS text, MACHINEHOURS text, AREAOFINVEST text, COORDINATESYST text, HEIGHTSYST text, MASL text, R10 text, R13 text

Bookmark: object_relations
Counter [off]
    CNT_ATTR = _count
    DOMAIN = counter
    SCOPE = Global
    START = 0
    -> FeatureMerger [REQUESTOR] [off]
RTYPE (reader XLSXR_1) [off]
    attributes: value number(1,0), base_text char(12), related_text char(12)
    -> FeatureMerger [SUPPLIER] [off]
FeatureMerger [off]
    ATTR_ACCUM_MODE = Merge Supplier
    ATTR_CONFLICT_RES_LOOKUP = REQUESTOR_IF_CONFLICT
    IGNORE_NULLS = No
    JOIN_KEYS = @Value(RTYPE) @Value(value) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> AttributeManager_3 [off]
AttributeManager_3 [off]
    ATTR_TABLE:
      RENAME_SET_VALUE _count > id
      SET_TO base_id = @Value(OBJECTNO)_@Value(SUBOBJECT)_0
      SET_TO related_id = @Value(COBJECTNO)_@Value(CSUBOBJECT)_0
    USER_EXPOSED_ATTRIBUTES = PROJECT,CATEGORY,OBJECTNO,SUBOBJECT,RTYPE,COBJECTNO,CSUBOBJECT,_count
    -> object_relations (writer SQLITE3_2) [off]
object_relations (writer SQLITE3_2) [off]
    attributes: id integer, base_id text, related_id text, base_text text, related_text text

Bookmark: gpkext_relations
Creator_2 [off]
    GEOMTYPE = Geometry Object
    NUM = 1
    CREATED -> AttributeManager_4 [off]
AttributeManager_4 [off]
    ATTR_TABLE:
      REMOVE _creation_instance
      SET_TO id = 1
      SET_TO base_table_name = objects
      SET_TO base_primary_column = OBJECTNO_SUBOBJECT_IDX
      SET_TO mapping_table_name = object_relations
      SET_TO related_primary_column = OBJECTNO_SUBOBJECT_IDX
      SET_TO related_table_name = objects
      SET_TO relation_name = obj2obj
    USER_EXPOSED_ATTRIBUTES = _creation_instance
    -> gpkgext_relations (writer SQLITE3_2) [off]
gpkgext_relations (writer SQLITE3_2) [off]
    attributes: id integer, base_table_name text, base_primary_column text, related_table_name text, related_primary_column text, relation_name text, mapping_table_name text,Unique

Bookmark: gpkg_extension
Creator [off]
    GEOMTYPE = Geometry Object
    NUM = 1
    CREATED -> AttributeManager [off]
    CREATED -> AttributeManager_2 [off]
AttributeManager [off]
    ATTR_TABLE:
      REMOVE _creation_instance
      SET_TO column_name
      SET_TO definition = http://www.geopackage.org/18-000.html
      SET_TO extension_name = related_tables
      SET_TO scope = read-write
      SET_TO table_name = object_relations
    -> gpkg_extensions (writer SQLITE3_2) [off]
AttributeManager_2 [off]
    ATTR_TABLE:
      REMOVE _creation_instance
      SET_TO column_name
      SET_TO definition = http://www.geopackage.org/18-000.html
      SET_TO extension_name = related_tables
      SET_TO scope = read-write
      SET_TO table_name = gpkgext_relations
    -> gpkg_extensions (writer SQLITE3_2) [off]
gpkg_extensions (writer SQLITE3_2) [off]
    attributes: table_name text,Unique, column_name text,Unique, extension_name text,Unique, definition text, scope text
