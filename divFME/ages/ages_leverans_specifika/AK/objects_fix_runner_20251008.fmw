FME workspace objects_fix_runner_20251008.fmw

Parameters:
- SourceDataset_PATH_3 = C:\ny_slask\AK-data\kolladubletter20251009\4_gpkg_till_säkerhetskontroll   # INCLUDE_WEB_BROWSER Source Folder and File Pathnames Folder_4
- SourceDataset_PATH = C:\ny_slask\AK-data\kolladubletter20251009\7_med z_kollade_avSL   # INCLUDE_WEB_BROWSER Source Folder and File Pathnames Folder_7
- DestDataset_XLSXW = C:\Github\kix\SiteWorks-Py\check_number_in_objects20251008.xlsx   # Destination Microsoft Excel File

Readers:
- PATH_1: PATH from $(SourceDataset_PATH)
- PATH_2: PATH from $(SourceDataset_PATH_3)

BulkAttributeRenamer
    ATTRCHOICE_ACTION = NONPROTECTEDFME
    MODE_CHOICE = RENAME
    PATTERN_ACTION_DISP = ADDPREFIX
    REPLACE_STR = 7_
    ATTRCHOICE = All Attributes
    -> Tester
Tester
    BOOL_OP = OR
    TEST_CLAUSE = CASE_INSENSITIVE_TEST @Value(7_path_rootname) NOT_BEGINS_WITH agg
    TEST_MODE = CASE_INSENSITIVE_TEST
    PASSED -> WorkspaceRunner
WorkspaceRunner
    BLOCKING = No
    MAX_TO_BATCH = 1
    OVERWRITE_LOG_FILE = HONOR
    WORKSPACE_FILE = $(FME_MF_DIR_ENCODED)objects_fix20251008.fmw
    WORKSPACE_PARAMETERS = SourceDataset_OGCGEOPACKAGE_3,@Value(4_path_windows),SourceDataset_OGCGEOPACKAGE,@Value(7_path_windows),DestDataset_XLSXW,$(DestDataset_XLSXW)
PATH (reader PATH_2)
    attributes: path_unix buffer, path_windows buffer, path_rootname buffer, path_filename buffer, path_extension buffer, path_directory_unix buffer, path_directory_windows buffer, path_type char(10)

Bookmark: 7_med_z
PATH (reader PATH_1)
    attributes: path_unix buffer, path_windows buffer, path_rootname buffer, path_filename buffer, path_extension buffer, path_directory_unix buffer, path_directory_windows buffer, path_type char(10)
    -> BulkAttributeRenamer
