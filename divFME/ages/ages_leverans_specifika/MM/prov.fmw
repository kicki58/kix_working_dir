FME workspace prov.fmw

Parameters:
- SourceDataset_MSSQL_ADO = MK7634   # Database
- DestDataset_XLSXW = C:\ny_slask\mm_2\prov.xlsx   # Destination Microsoft Excel File

Readers:
- MSSQL_ADO_1: MSSQL_ADO from $(SourceDataset_MSSQL_ADO)

Writers:
- XLSXW_1: XLSXW to $(DestDataset_XLSXW)

ClassDef (reader MSSQL_ADO_1)
    attributes: MetaId integer, CanAddSubclass smallint, SpecialRegIsActive smallint, InfoGroupDefId integer, DefaultAttributeDefId integer
Object (reader MSSQL_ADO_1)
    attributes: ObjectId identity, ClassId integer, SubClassid integer, Id integer, Name char(50), IsRegistered smallint, SiteId integer
    -> AttributeKeeper
AttributeKeeper
    CREATE_BULK_MODE_FEATURES = NO
    KEEP_ATTRS = ClassId,Id,ObjectId,SubClassid
    -> FeatureMerger [REQUESTOR]
ObjectDef (reader MSSQL_ADO_1)
    attributes: MetaId integer, Code char(10), Id integer, Color integer, CanAddAttribute smallint
Definition (reader MSSQL_ADO_1)
    attributes: MetaId identity, VersionReferenceId integer, Name char(50), Description varchar(100), ToolTip varchar(50), Help text, IsVisible smallint, ExternalId integer
    -> Tester
    -> FeatureMerger_2 [SUPPLIER]
Tester
    BOOL_OP = OR
    TEST_CLAUSE = TEST @Value(Name) = Provanalys
    TEST_MODE = TEST
    PASSED -> FeatureMerger [SUPPLIER]
FeatureMerger
    ATTR_ACCUM_MODE = Merge Supplier
    ATTR_CONFLICT_RES_LOOKUP = REQUESTOR_IF_CONFLICT
    IGNORE_NULLS = No
    JOIN_KEYS = @Value(ClassId) @Value(MetaId) AUTO
    MERGE_TYPE = Attributes Only
    PROCESS_DUPS = NO
    REJECT_NULL_MISSING_KEYS = No
    SUPPLIERS_FIRST = No
    ATTR_CONFLICT_RES = Use Requestor
    MERGED -> FeatureMerger_2 [REQUESTOR]
FeatureMerger_2
    ATTR_ACCUM_MODE = Merge Supplier
    ATTR_CONFLICT_RES_LOOKUP = REQUESTOR_IF_CONFLICT
    IGNORE_NULLS = No
    JOIN_KEYS = @Value(SubClassid) @Value(MetaId) AUTO
    MERGE_TYPE = Attributes Only
    PROCESS_DUPS = NO
    REJECT_NULL_MISSING_KEYS = No
    SUPPLIERS_FIRST = No
    ATTR_CONFLICT_RES = Use Requestor
    USED_SUPPLIER -> AttributeManager
AttributeManager
    ATTR_TABLE = SET_TO intrasis_db (varchar(200)) = $(SourceDataset_MSSQL_ADO)
    -> Sheet1 (writer XLSXW_1)
Sheet1 (writer XLSXW_1)
    attributes: MetaId number(20), VersionReferenceId number(20), Name string(50), Description string(100), ToolTip string(50), Help string(20), IsVisible number(20), ExternalId number(20), numReferences number(20), intrasis_db string(200)
