FME workspace 3_metaDataCreator_2_v2.fmw

Parameters:
- SourceDataset_OGCGEOPACKAGE = \\argos.storage.uu.se\MyFolder$\krima354\kicki_arbetsfiler\GETdata\arkeologiska_uppdrag_undersökningsområden_sverig.gpkg   # uo GeoPackage File
- SourceDataset_SHAPEFILE_5 = \\argos.storage.uu.se\MyFolder$\krima354\kicki_arbetsfiler\GETdata\shape_svenska_220223\KommunSweref99TM\Kommun_Sweref99TM_region.shp   # Kommun Source Esri Shapefile(s)
- SourceDataset_SHAPEFILE_4 = \\argos.storage.uu.se\MyFolder$\krima354\kicki_arbetsfiler\GETdata\shape_svenska_220223\LanSweref99TM\Lan_Sweref99TM_region.shp   # Lan Source Esri Shapefile(s)
- SourceDataset_SHAPEFILE = \\argos.storage.uu.se\MyFolder$\krima354\kicki_arbetsfiler\GETdata\Kopia av landskap_shp\landskap\svelandskap_2010_rev_granser.shp   # Landskakap Source Esri Shapefile(s)
- SourceDataset_OGCGEOPACKAGE_8 = \\argos.storage.uu.se\MyFolder$\krima354\kicki_arbetsfiler\GETdata\sockenstad.gpkg   # Socken GeoPackage File
- SourceDataset_OGCGEOPACKAGE_7 = C:\ny_slask\kolla_urdar20240624\hjalpfiler\all_geom.gpkg   # urdar alla geom GeoPackage File
- DestDataset_XLSXW = C:\ny_slask\kolla_urdar20240624\slutlev44.xlsx   # Destination Microsoft Excel File
- SourceDataset_OGCGEOPACKAGE_11 = C:\ny_slask\kolla_urdar20240624\hjalpfiler\intrasis_archive44.gpkg   # siteinfo GeoPackage File
- SourceDataset_CSV2 = \\argos.storage.uu.se\MyFolder$\krima354\kicki_arbetsfiler\urdar_arbetsfiler\create_siteinfo\alla_srid_20240221.csv   # Source CSV (Comma Separated Value) File(s)
- SourceDataset_OGCGEOPACKAGE_10 = C:\ny_slask\kolla_urdar20240624\hjalpfiler\proj_info_20240624.gpkg   # GeoPackage File

Readers:
- SHAPEFILE_1: SHAPEFILE from $(SourceDataset_SHAPEFILE) in EPSG:3006
- SHAPEFILE_2: SHAPEFILE from $(SourceDataset_SHAPEFILE_5) in EPSG:3006
- SHAPEFILE_3: SHAPEFILE from $(SourceDataset_SHAPEFILE_4) in EPSG:3006
- OGCGEOPACKAGE_3: OGCGEOPACKAGE from $(SourceDataset_OGCGEOPACKAGE_8) in EPSG:3006
- OGCGEOPACKAGE_1: OGCGEOPACKAGE from $(SourceDataset_OGCGEOPACKAGE) in EPSG:3006
- OGCGEOPACKAGE_4: OGCGEOPACKAGE from $(SourceDataset_OGCGEOPACKAGE_7) in EPSG:3006
- OGCGEOPACKAGE_2: OGCGEOPACKAGE from $(SourceDataset_OGCGEOPACKAGE_11) in EPSG:3006
- CSV2_1: CSV2 from $(SourceDataset_CSV2)
- OGCGEOPACKAGE_6: OGCGEOPACKAGE from $(SourceDataset_OGCGEOPACKAGE_10)

Writers:
- XLSXW_1: XLSXW to $(DestDataset_XLSXW)

CSV (reader CSV2_1)
    attributes: databas varchar(17), from_intrasis_epsg uint32
    -> AttributeManager_8
AttributeManager_8
    ATTR_TABLE = RENAME_SET_VALUE from_intrasis_epsg > epsg
    -> FeatureMerger_5 [SUPPLIER]
FeatureMerger_5
    ATTR_ACCUM_MODE = Merge Supplier
    ATTR_CONFLICT_RES = Use Requestor
    IGNORE_NULLS = No
    JOIN_KEYS = @Value(master_site_archive) @Value(databas) AUTO
    MERGE_TYPE = Attributes Only
    PROCESS_DUPS = NO
    REJECT_NULL_MISSING_KEYS = No
    SUPPLIERS_FIRST = No
    MERGED -> AttributeFilter_3
AttributeFilter_3
    ATTR_NAME = UUID_typ
    ATTR_VALUES = <Empty>,<Missing>,<Null>,<Unfiltered>,ej lyckats georeferera,empty,extern,manuell georeferering,noUUID,uppdaterat_UUID,UUID,uuidSattMen_empty
    ej lyckats georeferera -> AttributeManager_2
    empty -> AttributeManager_2
    extern -> AttributeManager_2
    manuell georeferering -> slutleverans (writer XLSXW_1)
    noUUID -> slutleverans (writer XLSXW_1)
    uppdaterat_UUID -> slutleverans (writer XLSXW_1)
    UUID -> slutleverans (writer XLSXW_1)
    uuidSattMen_empty -> slutleverans (writer XLSXW_1)
Note: sätt E, N tom
AttributeManager_2
    ATTR_TABLE:
      SET_TO E
      SET_TO N
    -> slutleverans (writer XLSXW_1)
slutleverans (writer XLSXW_1)
    attributes: master_site_archive string(17), master_site_name string(54), UUID_final string(37), UUID_final_finns string(200), UUID_final_link string(200), master_UUID string(37), master_UUID_finns string(200), link_master_uuid string(200), master_Uppdaterat UUID string(37), master_Uppdaterat UUID_finns string(200), master_link_Uppdaterat_uuid string(200), UUID_typ string(200), E number(20), N number(20), databas string(17), proj_info_intrasis_archive string(200), proj_info_pk number(20), proj_info_SiteId string(20), proj_info_Plats string(20), proj_info_Lst Dnr string(20), proj_info_Raä Dnr string(20), proj_info_Inventarienummer string(20), proj_info_Projektkod string(20), proj_info_Projektnamn string(20), proj_info_Projektledare string(20), proj_info_Uppdragsgivare string(20), proj_info_Exploateringstyp string(20), proj_info_Undersökningstyp string(20), proj_info_Slutdatum string(20), proj_info_Beskrivning string(20),
      _socken_concatenated string(20), _socken_antal number(20), _kommun_concatenated string(20), _kommun_antal number(20), _landskap_concatanted string(20), _landskap_antal number(20), _lan_concatenated string(20), _lan_antal number(20), uo_id string(255), uo_uppdragsnummer string(9), uo_beslutande_myndighet string(255), uo_beslutsdatum date(20), uo_diarienummer string(255), uo_uppdragstyp string(255), uo_utforande_organisation string(255), uo_nollresultat string(9), uo_url string(255), uo_status string(255), uo_lan string(20), uo_kommun string(20), uo_socken string(20), epsg number(20)

Bookmark: intrasis geometrier + UUID master
siteinfo (reader OGCGEOPACKAGE_2)
    attributes: master_site_archive text(17), master_site_name text(54), UUID_typ text(200), UUID_final text(37), UUID_final_finns text(200), UUID_final_link text(200), master_UUID text(37), master_UUID_finns text(200), link_master_uuid text(200), master_Uppdaterat UUID text(37), master_Uppdaterat UUID_finns text(200), master_link_Uppdaterat_uuid text(200), id int,PrimaryKey
    -> GeometryRemover
GeometryRemover
    -> AttributeManager_5
AttributeManager_5
    -> FeatureMerger [REQUESTOR]
geom (reader OGCGEOPACKAGE_4)
    attributes: intrasis_archive text(200), id int,PrimaryKey
    -> GeometryFilter
GeometryFilter
    FILTER_MODE = SIMPLE
    FILTER_MULTI = FILTER_TYPES]Area]FME_CONTROLLER_QUERY_FILE]]FME_CONTROLLER_CHOICE]Simple
    Area -> Aggregator
    <UNFILTERED> -> Bufferer
Bufferer
    ANGLE = 22.5
    CAP_STYLE = Arc
    CORNER_STYLE = Arc
    MODE = AREA
    OFFSET = 0.01
    OFFSET_UNITS = METERS
    PRECISION = APPROX
    BUFFERED -> Aggregator
Aggregator
    ACCUM_ATTRS_NAME = Use Attributes From One Feature
    AGGREGATE_TYPE = Homogeneous Collection (If Possible)
    COUNT_ATTR = num_features
    GROUP_BY = intrasis_archive
    MODE = Geometry - Assemble One Level
    SEP = ,
    AGGREGATE -> BulkAttributeRenamer_3
BulkAttributeRenamer_3
    ATTRCHOICE = All Attributes
    MODE_CHOICE = RENAME
    PATTERN_ACTION_DISP = ADDPREFIX
    REPLACE_STR = geom_
    -> FeatureMerger [SUPPLIER]
FeatureMerger
    ATTR_ACCUM_MODE = Merge Supplier
    ATTR_CONFLICT_RES = Use Requestor
    IGNORE_NULLS = No
    JOIN_KEYS = @Value(master_site_archive) @Value(geom_intrasis_archive) AUTO
    MERGE_TYPE = Attributes and Geometry
    PROCESS_DUPS = NO
    REJECT_NULL_MISSING_KEYS = No
    SUPPLIERS_FIRST = No
    MERGED -> AttributeRemover_2
    UNMERGED_REQUESTOR -> AttributeRemover_2
AttributeRemover_2
    REMOVE_ATTRS = geom_nuber_of_areas,geom_num_features,master_H,geom_id,geom_intrasis_archive,geom_intrasisarchive,numOfFeature
    -> SpatialRelator [Requestor]

Bookmark: socken
sockenstad (reader OGCGEOPACKAGE_3)
    attributes: objektidentitet text(36), objektversion smallint, version_giltig_fran text(16), sockenstadkod text(4), sockenstadnamn text(100), sockenstadtyp smallint, omradesnummer smallint, huvudomrade text(1), sockenstadanmarkning text(254), OBJECTID int,PrimaryKey
    -> AttributeRemover
AttributeRemover
    REMOVE_ATTRS = huvudomrade,OBJECTID,objektidentitet,objektversion,omradesnummer,sockenstadanmarkning,version_giltig_fran
    -> SpatialRelator [Supplier]
SpatialRelator
    AGGREGATE_HANDLING = Yes
    CALC_CARD = No
    CURVE_BOUNDARY_RULE_PARAM = Default Rule
    LIST_ATTRS_TO_INCLUDE = sockenstadnamn
    LIST_NAME = _relationships
    PREDICATES = WITHIN CONTAINS INTERSECTS
    SUCCESS_ATTR = _socken_antal
    -> ListConcatenator
    <Rejected> -> ListConcatenator
ListConcatenator
    DROP_EMPTY_PARTS = No
    LIST_ATTR = _relationships{}.sockenstadnamn
    SEP = |
    VAL_ATTR = _socken_concatenated
    -> AttributeRemover_3
AttributeRemover_3
    LIST_ATTRS = _relationships{} _relationships{}.de9im _relationships{}.pass{} _relationships{}.sockenstadnamn
    REMOVE_ATTRS = _list_index,_related_suppliers,agg_feat,fme_rejection_code,sockenstadkod,sockenstadnamn,sockenstadtyp
    -> AttributeManager
AttributeManager
    -> SpatialRelator_2 [Requestor]

Bookmark: Landskap
svelandskap_2010_rev_granser (reader SHAPEFILE_1)
    attributes: LANDSKAP varchar(254), ID number(16,0), KOMMENTAR varchar(150), SKALA varchar(100), AREA_METER double, PERIMETER_ double, HECTARES double
    -> AttributeRemover_6
AttributeRemover_6
    REMOVE_ATTRS = AREA_METER,HECTARES,ID,KOMMENTAR,PERIMETER_,SKALA
    -> SpatialRelator_4 [Supplier]
SpatialRelator_4
    AGGREGATE_HANDLING = Yes
    CALC_CARD = No
    CURVE_BOUNDARY_RULE_PARAM = Default Rule
    LIST_ATTRS_TO_INCLUDE = LANDSKAP
    LIST_NAME = _relationships
    PREDICATES = WITHIN CONTAINS INTERSECTS
    SUCCESS_ATTR = _landskap_antal
    -> ListConcatenator_4
    <Rejected> -> ListConcatenator_4
ListConcatenator_4
    DROP_EMPTY_PARTS = No
    LIST_ATTR = _relationships{}.LANDSKAP
    SEP = |
    VAL_ATTR = _landskap_concatanted
    -> AttributeManager_4
AttributeManager_4
    ATTR_TABLE:
      REMOVE _relationships{}.de9im
      REMOVE _relationships{}.pass{}
      REMOVE _relationships{}.LANDSKAP
      REMOVE fme_rejection_code
      REMOVE LANDSKAP
    -> FeatureMerger_2 [REQUESTOR]

Bookmark: kommun
Kommun_Sweref99TM_region (reader SHAPEFILE_2)
    attributes: KnKod varchar(4), KnNamn varchar(15)
    -> AttributeRemover_5
AttributeRemover_5
    REMOVE_ATTRS = KnKod
    -> SpatialRelator_2 [Supplier]
SpatialRelator_2
    AGGREGATE_HANDLING = Yes
    CALC_CARD = No
    CURVE_BOUNDARY_RULE_PARAM = Default Rule
    LIST_ATTRS_TO_INCLUDE = KnNamn
    LIST_NAME = _relationships
    PREDICATES = WITHIN CONTAINS INTERSECTS
    SUCCESS_ATTR = _kommun_antal
    -> ListConcatenator_2
    <Rejected> -> ListConcatenator_2
ListConcatenator_2
    DROP_EMPTY_PARTS = No
    LIST_ATTR = _relationships{}.KnNamn
    SEP = |
    VAL_ATTR = _kommun_concatenated
    -> AttributeManager_6
AttributeManager_6
    ATTR_TABLE:
      REMOVE _relationships{}.KnNamn
      REMOVE _relationships{}.de9im
      REMOVE _relationships{}.pass{}
      REMOVE KnNamn
    -> SpatialRelator_3 [Requestor]

Bookmark: lan
Lan_Sweref99TM_region (reader SHAPEFILE_3)
    attributes: LnKod varchar(2), LnNamn varchar(20)
    -> AttributeRemover_4
AttributeRemover_4
    REMOVE_ATTRS = LnKod
    -> SpatialRelator_3 [Supplier]
SpatialRelator_3
    AGGREGATE_HANDLING = Yes
    CALC_CARD = No
    CURVE_BOUNDARY_RULE_PARAM = Default Rule
    LIST_ATTRS_TO_INCLUDE = LnNamn
    LIST_NAME = _relationships
    PREDICATES = WITHIN CONTAINS INTERSECTS
    SUCCESS_ATTR = _lan_antal
    -> ListConcatenator_3
    <Rejected> -> ListConcatenator_3
ListConcatenator_3
    DROP_EMPTY_PARTS = No
    LIST_ATTR = _relationships{}.LnNamn
    SEP = |
    VAL_ATTR = _lan_concatenated
    -> AttributeManager_3
AttributeManager_3
    ATTR_TABLE:
      REMOVE _relationships{}.LnNamn
      REMOVE _relationships{}.de9im
      REMOVE _relationships{}.pass{}
      REMOVE LnNamn
    -> SpatialRelator_4 [Requestor]

Bookmark: koordinater
point_median (reader OGCGEOPACKAGE_4)
    attributes: intrasis_archive text(200), id int,PrimaryKey
    -> CoordinateExtractor_2
CoordinateExtractor_2
    IND = 0
    MODE = Specify Coordinate
    X_ATTR = _x
    Y_ATTR = _y
    Z_ATTR = _z
    -> AttributeManager_7
AttributeManager_7
    ATTR_TABLE:
      REMOVE id
      RENAME_SET_VALUE _x > E
      RENAME_SET_VALUE _y > N
      REMOVE _z
    -> GeometryRemover_2
GeometryRemover_2
    -> FeatureMerger_2 [SUPPLIER]
FeatureMerger_2
    ATTR_ACCUM_MODE = Merge Supplier
    ATTR_CONFLICT_RES = Use Requestor
    IGNORE_NULLS = No
    JOIN_KEYS = @Value(master_site_archive) @Value(intrasis_archive) AUTO
    MERGE_TYPE = Attributes and Geometry
    PROCESS_DUPS = NO
    REJECT_NULL_MISSING_KEYS = No
    SUPPLIERS_FIRST = No
    MERGED -> FeatureMerger_3 [REQUESTOR]
    UNMERGED_REQUESTOR -> FeatureMerger_3 [REQUESTOR]

Bookmark: project_information
projec_information (reader OGCGEOPACKAGE_6)
    attributes: proj_info_intrasis_archive text(200), proj_info_pk mediumint, proj_info_SiteId text, proj_info_Plats text, proj_info_Lst Dnr text, proj_info_Raä Dnr text, proj_info_Inventarienummer text, proj_info_Projektkod text, proj_info_Projektnamn text, proj_info_Projektledare text, proj_info_Uppdragsgivare text, proj_info_Exploateringstyp text, proj_info_Undersökningstyp text, proj_info_Slutdatum text, proj_info_Beskrivning text, proj_info_fid int, id int,PrimaryKey
    -> FeatureMerger_3 [SUPPLIER]
Note: OBS Kolla upp denna
FeatureMerger_3
    ATTR_ACCUM_MODE = Merge Supplier
    ATTR_CONFLICT_RES = Use Requestor
    IGNORE_NULLS = No
    JOIN_KEYS = @Value(master_site_archive) @Value(proj_info_intrasis_archive) AUTO
    MERGE_TYPE = Attributes and Geometry
    PROCESS_DUPS = NO
    REJECT_NULL_MISSING_KEYS = No
    SUPPLIERS_FIRST = No
    MERGED -> FeatureMerger_4 [REQUESTOR]
    UNMERGED_REQUESTOR -> FeatureMerger_4 [REQUESTOR]

Bookmark: uom
arkeologiska_uppdrag_undersökningsområden_sverige_linestring (reader OGCGEOPACKAGE_1)
    attributes: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
arkeologiska_uppdrag_undersökningsområden_sverige_polygon (reader OGCGEOPACKAGE_1)
    attributes: id text(255), uppdragsnummer text(9), beslutande_myndighet text(255), beslutsdatum date, diarienummer text(255), uppdragstyp text(255), utforande_organisation text(255), nollresultat text(9), url text(255), status text(255), lan text, kommun text, socken text, fid int,PrimaryKey
    -> BulkAttributeRenamer
arkeologiska_uppdrag_undersökningsområden_sverige_point (reader OGCGEOPACKAGE_1)
    attributes: id text(255), uppdragsnummer text(9), beslutande_myndighet text(255), beslutsdatum date, diarienummer text(255), uppdragstyp text(255), utforande_organisation text(255), nollresultat text(9), url text(255), status text(255), lan text, kommun text, socken text, fid int,PrimaryKey
    -> BulkAttributeRenamer
BulkAttributeRenamer
    ATTRCHOICE = All Attributes
    MODE_CHOICE = RENAME
    PATTERN_ACTION_DISP = ADDPREFIX
    REPLACE_STR = uo_
    -> FeatureMerger_4 [SUPPLIER]
FeatureMerger_4
    ATTR_ACCUM_MODE = Merge Supplier
    ATTR_CONFLICT_RES = Use Requestor
    IGNORE_NULLS = No
    JOIN_KEYS = @Value(UUID_final) @Value(uo_id) AUTO
    MERGE_TYPE = Attributes Only
    PROCESS_DUPS = NO
    REJECT_NULL_MISSING_KEYS = No
    SUPPLIERS_FIRST = No
    MERGED -> AttributeManager_9
    UNMERGED_REQUESTOR -> AttributeManager_9
AttributeManager_9
    ATTR_TABLE:
      REMOVE uo_fid
      REMOVE id
      REMOVE proj_info_fid
      REMOVE intrasis_archive
    -> FeatureMerger_5 [REQUESTOR]
