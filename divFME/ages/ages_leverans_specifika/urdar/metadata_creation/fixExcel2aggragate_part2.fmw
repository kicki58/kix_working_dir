FME workspace fixExcel2aggragate_part2.fmw

Parameters:
- SourceDataset_POSTGIS = postgres@external-ages   # Connection
- SourceDataset_PATH = C:\ny_slask\aggragate   # INCLUDE_WEB_BROWSER Source Folder and File Pathnames Folder
- SourceDataset_XLSXR_3 = C:\Users\krima354\Box\Urdar\gpkg_csv\alla_gpkg_csv_slutleverans\tillRAA20240624_v4_bearbetning4aggregate.xlsx   # Source Microsoft Excel File(s)
- SourceDataset_XLSXR = C:\ny_slask\tillRAA20240624_v4_bearbetad.xlsx   # Source Microsoft Excel File(s)
- DestDataset_FILECOPY = C:\ny_slask\aggragate   # Destination File Copy Folder

Readers:
- POSTGIS_1: POSTGIS from $(SourceDataset_POSTGIS)
- PATH_1: PATH from $(SourceDataset_PATH)
- XLSXR_1: XLSXR from $(SourceDataset_XLSXR)
- XLSXR_2: XLSXR from $(SourceDataset_XLSXR_3)

Writers:
- FILECOPY_1: FILECOPY to $(DestDataset_FILECOPY)

ej lyckats georeferera (reader XLSXR_2)
    attributes: efterbearbetning char(22), master_site_archive char(9), master_site_name char(42), UUID_final string, UUID_final_finns string, UUID_final_link string, master_UUID char(36), master_UUID_finns char(3), link_master_uuid char(76), master_Uppdaterat UUID char(36), master_Uppdaterat UUID_finns char(2), master_link_Uppdaterat_uuid char(76), UUID_typ char(22), E char(1), N char(1), databas char(9), proj_info_intrasis_archive char(9), proj_info_pk number(1,0), proj_info_SiteId char(10), proj_info_Plats char(26), proj_info_Lst Dnr char(14), proj_info_Raä Dnr char(13), proj_info_Inventarienummer char(12), proj_info_Projektkod char(9), proj_info_Projektnamn char(35), proj_info_Projektledare char(23), proj_info_Uppdragsgivare char(31), proj_info_Exploateringstyp char(13), proj_info_Undersökningstyp char(23), proj_info_Slutdatum char(10),
      proj_info_Beskrivning char(1), _socken_concatenated char(8), _socken_antal number(1,0), _kommun_concatenated char(10), _kommun_antal number(1,0), _landskap_concatanted char(12), _landskap_antal number(1,0), _lan_concatenated char(7), _lan_antal number(1,0), uo_id string, uo_uppdragsnummer string, uo_beslutande_myndighet string, uo_beslutsdatum string, uo_diarienummer string, uo_uppdragstyp string, uo_utforande_organisation string, uo_nollresultat string, uo_url string, uo_status string, uo_lan string, uo_kommun string, uo_socken string, epsg number(4,0)
    -> Tester
UUID_finns&inomSverige (reader XLSXR_2)
    attributes: efterbearbetning char(22), master_site_archive char(10), master_site_name char(52), UUID_final char(36), UUID_final_finns char(2), UUID_final_link char(76), master_UUID char(36), master_UUID_finns char(3), link_master_uuid char(76), master_Uppdaterat UUID char(36), master_Uppdaterat UUID_finns char(3), master_link_Uppdaterat_uuid char(76), UUID_typ char(21), E number(20,13), N number(21,13), databas char(10), proj_info_intrasis_archive char(10), proj_info_pk number(1,0), proj_info_SiteId char(10), proj_info_Plats char(48), proj_info_Lst Dnr char(35), proj_info_Raä Dnr char(41), proj_info_Inventarienummer char(11), proj_info_Projektkod char(23), proj_info_Projektnamn char(54), proj_info_Projektledare char(37), proj_info_Uppdragsgivare char(44), proj_info_Exploateringstyp char(27), proj_info_Undersökningstyp char(30), proj_info_Slutdatum char(10),
      proj_info_Beskrivning char(4944), _socken_concatenated char(259), _socken_antal number(2,0), _kommun_concatenated char(50), _kommun_antal number(1,0), _landskap_concatanted char(29), _landskap_antal number(1,0), _lan_concatenated char(29), _lan_antal number(1,0), uo_id char(36), uo_uppdragsnummer number(9,0), uo_beslutande_myndighet char(40), uo_beslutsdatum date, uo_diarienummer char(16), uo_uppdragstyp char(29), uo_utforande_organisation char(55), uo_nollresultat char(3), uo_url char(90), uo_status char(10), uo_lan char(26), uo_kommun char(44), uo_socken char(151), epsg number(4,0)
    -> Tester
empty (reader XLSXR_2)
    attributes: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
uuidSattMen_empty (reader XLSXR_2)
    attributes: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
sammanfattning_antal (reader XLSXR_2)
    attributes: UUID_finns&inomSverige number(4,0), ej_lyckats_georeferera number(2,0), empty number(3,0), no_uuid number(3,0), extern number(2,0), uuidSattMenEmpty number(1,0), summa number(4,0)
PATH (reader PATH_1)
    attributes: path_unix buffer, path_windows buffer, path_rootname buffer, path_filename buffer, path_extension buffer, path_directory_unix buffer, path_directory_windows buffer, path_type char(10)
    -> AttributeManager
AttributeManager
    ATTR_TABLE = RENAME_SET_VALUE path_windows > filecopy_source_dataset (buffer)
    -> FeatureMerger [SUPPLIER]
    -> FeatureMerger_4 [SUPPLIER]
utanfor_sverige (reader XLSXR_1)
    attributes: master_site_archive char(10)
    -> FeatureMerger_2 [SUPPLIER]
noUUID (reader XLSXR_2)
    attributes: efterbearbetning char(6), master_site_archive char(16), master_site_name char(32), UUID_final string, UUID_final_finns string, UUID_final_link string, master_UUID string, master_UUID_finns string, link_master_uuid string, master_Uppdaterat UUID char(1), master_Uppdaterat UUID_finns string, master_link_Uppdaterat_uuid string, UUID_typ char(6), E number(21,13), N number(21,13), databas char(16), proj_info_intrasis_archive char(16), proj_info_pk number(1,0), proj_info_SiteId char(16), proj_info_Plats char(53), proj_info_Lst Dnr char(28), proj_info_Raä Dnr char(14), proj_info_Inventarienummer char(13), proj_info_Projektkod char(14), proj_info_Projektnamn char(56), proj_info_Projektledare char(42), proj_info_Uppdragsgivare char(38), proj_info_Exploateringstyp char(41), proj_info_Undersökningstyp char(23), proj_info_Slutdatum char(10),
      proj_info_Beskrivning char(1710), _socken_concatenated char(1349), _socken_antal number(3,0), _kommun_concatenated char(162), _kommun_antal number(2,0), _landskap_concatanted char(34), _landskap_antal number(1,0), _lan_concatenated char(47), _lan_antal number(1,0), uo_id string, uo_uppdragsnummer string, uo_beslutande_myndighet string, uo_beslutsdatum string, uo_diarienummer string, uo_uppdragstyp string, uo_utforande_organisation string, uo_nollresultat string, uo_url string, uo_status string, uo_lan string, uo_kommun string, uo_socken string, epsg number(4,0)
    -> Tester
Tester
    BOOL_OP = OR
    TEST_CLAUSE = TEST 1 = 1
    TEST_MODE = TEST
    PASSED -> FeatureMerger_3 [SUPPLIER]
geodata_info (reader POSTGIS_1)
    attributes: geodatafil text, uppdragsnummer text, uppdragstyp text, diarienummer text, utforande_organisation text, beslutande_myndighet text, beslutsdatum text, kommun text, lan text, socken text, link_geodata text, link_fornsok text, forfattare varchar, titel varchar, utgivningsar varchar, link_rapport_info varchar
    -> FeatureMerger [REQUESTOR]
    -> FeatureMerger_3 [REQUESTOR]
FeatureMerger
    ATTR_ACCUM_MODE = Merge Supplier
    ATTR_CONFLICT_RES_LOOKUP = REQUESTOR_IF_CONFLICT
    IGNORE_NULLS = No
    JOIN_KEYS = @Value(geodatafil) @Value(path_rootname) AUTO
    MERGE_TYPE = Attributes Only
    PROCESS_DUPS = NO
    REJECT_NULL_MISSING_KEYS = No
    SUPPLIERS_FIRST = No
    ATTR_CONFLICT_RES = Use Requestor
    UNUSED_SUPPLIER -> FeatureMerger_2 [REQUESTOR]
FeatureMerger_2
    ATTR_ACCUM_MODE = Merge Supplier
    ATTR_CONFLICT_RES_LOOKUP = REQUESTOR_IF_CONFLICT
    IGNORE_NULLS = No
    JOIN_KEYS = @Value(path_rootname) @Value(master_site_archive) AUTO
    MERGE_TYPE = Attributes Only
    PROCESS_DUPS = NO
    REJECT_NULL_MISSING_KEYS = No
    SUPPLIERS_FIRST = No
    ATTR_CONFLICT_RES = Use Requestor
FeatureMerger_3
    ATTR_ACCUM_MODE = Merge Supplier
    ATTR_CONFLICT_RES_LOOKUP = REQUESTOR_IF_CONFLICT
    IGNORE_NULLS = No
    JOIN_KEYS = @Value(geodatafil) @Value(master_site_archive) AUTO
    MERGE_TYPE = Attributes Only
    PROCESS_DUPS = NO
    REJECT_NULL_MISSING_KEYS = No
    SUPPLIERS_FIRST = No
    ATTR_CONFLICT_RES = Use Requestor
    MERGED -> AttributeFilter
    UNUSED_SUPPLIER -> AttributeFilter_2
AttributeFilter
    ATTR_NAME = efterbearbetning
    ATTR_VALUES = <Empty>,<Missing>,<Null>,<Unfiltered>,ej lyckats georeferera,noUUID,UUID_finns&inomSverige
AttributeFilter_2
    ATTR_NAME = efterbearbetning
    ATTR_VALUES = <Empty>,<Missing>,<Null>,<Unfiltered>,ej lyckats georeferera,noUUID,UUID_finns&inomSverige
    ej lyckats georeferera -> FeatureMerger_4 [REQUESTOR]
    UUID_finns&inomSverige -> FeatureMerger_4 [REQUESTOR]
extern (reader XLSXR_2)
    attributes: efterbearbetning char(6), master_site_archive char(10), master_site_name char(24), UUID_final string, UUID_final_finns string, UUID_final_link string, master_UUID string, master_UUID_finns string, link_master_uuid string, master_Uppdaterat UUID string, master_Uppdaterat UUID_finns string, master_link_Uppdaterat_uuid string, UUID_typ char(6), E char(1), N char(1), databas char(10), proj_info_intrasis_archive char(10), proj_info_pk number(1,0), proj_info_SiteId char(11), proj_info_Plats char(1), proj_info_Lst Dnr char(1), proj_info_Raä Dnr char(1), proj_info_Inventarienummer char(1), proj_info_Projektkod char(1), proj_info_Projektnamn char(4), proj_info_Projektledare char(20), proj_info_Uppdragsgivare char(1), proj_info_Exploateringstyp char(1), proj_info_Undersökningstyp char(1), proj_info_Slutdatum char(1),
      proj_info_Beskrivning char(2061), _socken_concatenated char(12), _socken_antal number(1,0), _kommun_concatenated char(12), _kommun_antal number(1,0), _landskap_concatanted char(6), _landskap_antal number(1,0), _lan_concatenated char(6), _lan_antal number(1,0), uo_id string, uo_uppdragsnummer string, uo_beslutande_myndighet string, uo_beslutsdatum string, uo_diarienummer string, uo_uppdragstyp string, uo_utforande_organisation string, uo_nollresultat string, uo_url string, uo_status string, uo_lan string, uo_kommun string, uo_socken string, epsg number(5,0)
    -> FeatureMerger_4 [REQUESTOR]
FeatureMerger_4
    ATTR_ACCUM_MODE = Merge Supplier
    ATTR_CONFLICT_RES_LOOKUP = REQUESTOR_IF_CONFLICT
    IGNORE_NULLS = No
    JOIN_KEYS = @Value(master_site_archive) @Value(path_rootname) AUTO
    MERGE_TYPE = Attributes Only
    PROCESS_DUPS = NO
    REJECT_NULL_MISSING_KEYS = No
    SUPPLIERS_FIRST = No
    ATTR_CONFLICT_RES = Use Requestor
    MERGED -> att_kolla_upp (writer FILECOPY_1)
att_kolla_upp (writer FILECOPY_1)
