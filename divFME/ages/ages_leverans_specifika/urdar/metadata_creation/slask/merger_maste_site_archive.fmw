FME workspace merger_maste_site_archive.fmw

Parameters:
- SourceDataset_OGCGEOPACKAGE = C:\Users\krima354\Box\Urdar\uuid_check\all_intrasisArchive_20231213_5.gpkg   # GeoPackage File
- SourceDataset_OGCGEOPACKAGE_9 = C:\Users\krima354\Box\Urdar\uuid_check\intrasis_archive_UUID_master.gpkg   # GeoPackage File
- SourceDataset_CSV2 = C:\Users\krima354\Box\Urdar\uuid_check\felaktiga_geom.csv   # Source CSV (Comma Separated Value) File(s)
- SourceDataset_OGCGEOPACKAGE_6 = C:\Users\krima354\Work Folders\Documents\kicki_arbetsfiler\GETdata\Sverige_kl.gpkg   # GeoPackage File
- PASSWORD =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   # Password
- SourceDataset_OGCGEOPACKAGE_8 = C:\Users\krima354\Box\Urdar\uuid_check\urdar_all_geom20240116.gpkg   # GeoPackage File
- DestDataset_OGCGEOPACKAGE = C:\Users\krima354\Box\Urdar\uuid_check\till_RAA.gpkg   # GeoPackage File
- DestDataset_XLSXW = C:\Users\krima354\Box\Urdar\uuid_check\till_RAA.xls   # Destination Microsoft Excel File
- SourceDataset_XLSXR = C:\Users\krima354\Box\Urdar\Geom_fixed_SL_20231208\Arbetsfil_SL_2023_12_11_översikt_geom_check_lista.xlsx   # Source Microsoft Excel File(s)

Readers:
- OGCGEOPACKAGE_1: OGCGEOPACKAGE from $(SourceDataset_OGCGEOPACKAGE) in EPSG:3006
- OGCGEOPACKAGE_2: OGCGEOPACKAGE from $(SourceDataset_OGCGEOPACKAGE_9) in EPSG:3006
- CSV2_1: CSV2 from $(SourceDataset_CSV2)
- OGCGEOPACKAGE_4: OGCGEOPACKAGE from $(SourceDataset_OGCGEOPACKAGE_6) in EPSG:3006
- OGCGEOPACKAGE_5: OGCGEOPACKAGE from $(SourceDataset_OGCGEOPACKAGE_8) in EPSG:3006
- XLSXR_1: XLSXR from $(SourceDataset_XLSXR)

Writers:
- OGCGEOPACKAGE_3: OGCGEOPACKAGE to $(DestDataset_OGCGEOPACKAGE) in EPSG:3006
- XLSXW_1: XLSXW to $(DestDataset_XLSXW)

UUID_master_final20231212 (reader OGCGEOPACKAGE_2)
    attributes: intrasisarchive text(200), pk mediumint, SiteId text, Plats text, Lst Dnr text, Raä Dnr text, Inventarienummer text, Projektkod text, Projektnamn text, Projektledare text, Uppdragsgivare text, Exploateringstyp text, Undersökningstyp text, Slutdatum text, Beskrivning text, fid int, id int, lage text(200), numOfFeature int, geom_intrasisarchive text(200), agg_feat int, UUID_kix text(200), master_site_name text(54), master_site_archive text(17), master_uppdrag_nr int, master_kmr_uppdragsnummer int, master_UUID text(37), master_kmr_id text(37), master_Uppdaterat UUID text(37), master_Kommentar text(685),
      master_H text(4), master_col9 text(74), master__length_uppdrag_nr text(20), link_fornsok text(200), master_uppdrag_ny text(200), _relationships.undersokningsomraden_id text, _relationships.de9im text, _relationships.pass text, _related_suppliers int, ok_kix text(200), project_info_intrasisarchive text(200), project_info_pk mediumint, project_info_SiteId text, project_info_Plats text, project_info_Lst Dnr text, project_info_Raä Dnr text, project_info_Inventarienummer text, project_info_Projektkod text, project_info_Projektnamn text, project_info_Projektledare text, project_info_Uppdragsgivare text, project_info_Exploateringstyp text, project_info_Undersökningstyp text, project_info_Slutdatum text, project_info_Beskrivning text, project_info_fid int, project_info_id int, Geoobjekt_manuellt_georefererade mediumint, Georeferering_precision text(200), datname text,
      type_kix text(200), _traff_med_uo_id text, traff_undersokningsomraden_id text(255), traff_de9im text, traff_pass text, _list_index int, id_0 int,PrimaryKey
    -> FeatureMerger [REQUESTOR]
siteinfo_concat_2 (reader OGCGEOPACKAGE_1)
    attributes: intrasis_archive text(200), _id_fr_upp text, _kommun text, _kommun_fr_upp text, _lan text, _lan_fr_upp text, _landskap text, _socken_stad text, _socken_fr_upp text, _diarienummer_fr_upp text, _beslutande_myndighet_fr_upp text, _uppdragsnummer_fr_upp text, _utförande_org_fr_upp text, id int,PrimaryKey
    -> FeatureMerger [SUPPLIER]
    -> FeatureMerger_6 [REQUESTOR]
Note: join uuid_master med / site_info_concat
FeatureMerger
    ATTR_ACCUM_MODE = Merge Supplier
    ATTR_CONFLICT_RES = Use Requestor
    IGNORE_NULLS = No
    JOIN_KEYS = @Value(master_site_archive) @Value(intrasis_archive) AUTO
    MERGE_TYPE = Attributes Only
    PROCESS_DUPS = NO
    REJECT_NULL_MISSING_KEYS = No
    SUPPLIERS_FIRST = No
    MERGED -> AttributeManager_13
    UNMERGED_REQUESTOR -> FeatureMerger_2 [REQUESTOR]
Note: fixa de 16 som har fel type empty när det finns geom
AttributeManager_13
    ATTR_TABLE = SET_TO type_kix = FME_CONDITIONAL:DEFAULT_VALUE'_FME_NO_OP_'BOOL_OP;OR;COMPOSITE_TEST;1;TEST @Value(type_kix) = empty'check_uuid'FME_NUM_CONDITIONS2___
    -> FeatureMerger_2 [REQUESTOR]
point_median (reader OGCGEOPACKAGE_5)
    attributes: intrasis_archive text(200), id int,PrimaryKey
    -> FeatureMerger_2 [SUPPLIER]
    -> FeatureMerger_6 [SUPPLIER]
Note: join with median
FeatureMerger_2
    ATTR_ACCUM_MODE = Merge Supplier
    ATTR_CONFLICT_RES = Use Requestor
    IGNORE_NULLS = No
    JOIN_KEYS = @Value(master_site_archive) @Value(intrasis_archive) AUTO
    MERGE_TYPE = Attributes and Geometry
    PROCESS_DUPS = NO
    REJECT_NULL_MISSING_KEYS = No
    SUPPLIERS_FIRST = No
    MERGED -> AttributeManager
    UNMERGED_REQUESTOR -> AttributeManager
Note: ar till 4 archive-attribute som försvunnit av någon anledning / INGA VIKTIGA!
AttributeManager
    ATTR_TABLE:
      REMOVE geom_intrasisarchive
      REMOVE project_info_intrasisarchive
      REMOVE intrasis_archive
      REMOVE intrasisarchive
      REMOVE fid
      REMOVE id
    -> TestFilter
AttributeManager_3
    ATTR_TABLE:
      REMOVE Raä Dnr
      REMOVE Projektkod
      REMOVE Projektnamn
      REMOVE Projektledare
      REMOVE Uppdragsgivare
      REMOVE Undersökningstyp
      REMOVE Slutdatum
      REMOVE pk
      REMOVE Plats
      REMOVE id_0
      REMOVE Inventarienummer
      REMOVE Exploateringstyp
      REMOVE Beskrivning
      REMOVE lage
      REMOVE numOfFeature
      REMOVE _relationships.undersokningsomraden_id
      REMOVE _relationships.de9im
      REMOVE _relationships.pass
      REMOVE _related_suppliers
      REMOVE agg_feat
      REMOVE link_fornsok
      REMOVE SiteId
      REMOVE traff_de9im
      REMOVE traff_pass
      REMOVE _list_index
      REMOVE _id_fr_upp
      REMOVE master_H
      REMOVE master_col9
    -> TestFilter_2
Note: Remove UUIDkix om den redan finns i någon av de andra fälten
TestFilter_2
    DEFAULT_VALUE = <UNFILTERED>
    PASSED_TEST_GROUP_OUTPUT = FIRST
    TEST_LIST = "BOOL_OP,OR,COMPOSITE_TEST,""""""1"""""",TEST_CLAUSE,TEST @Value(UUID_kix) = @Value(master_UUID)",@Value(UUID_kix) = @Value(master_UUID),"BOOL_OP,OR,COMPOSITE_TEST,""""""1"""""",TEST_CLAUSE,TEST @Value(UUID_kix) = @Value(master_Uppdaterat UUID)",master_Uppdaterat UUID
    @Value(UUID_kix) = @Value(master_UUID) -> AttributeManager_4
    master_Uppdaterat UUID -> AttributeManager_4
    <UNFILTERED> -> AttributeManager_5
AttributeManager_4
    ATTR_TABLE = SET_TO UUID_kix
    -> AttributeManager_6
AttributeManager_5
    -> AttributeManager_6
AttributeManager_6
    ATTR_TABLE = RENAME_SET_VALUE UUID_kix > UUID_andrat_av_uu
    -> GeometryFilter
Note: tarbort tomma archives
Note: tar bort tomma intrasisarkiv
GeometryFilter
    FILTER_MODE = SIMPLE
    FILTER_MULTI = FILTER_TYPES]Null]FME_CONTROLLER_QUERY_FILE]]FME_CONTROLLER_CHOICE]Simple
    Null -> TestFilter_7
    <UNFILTERED> -> TestFilter_3
Note: tar bort externa arkiv
TestFilter_3
    DEFAULT_VALUE = <UNFILTERED>
    PASSED_TEST_GROUP_OUTPUT = FIRST
    TEST_LIST = "BOOL_OP,OR,COMPOSITE_TEST,""""""1"""""",TEST_CLAUSE,CASE_INSENSITIVE_TEST @Value(master_site_archive) BEGINS_WITH e",extern
    extern -> TestFilter_7
    <UNFILTERED> -> FeatureMerger_5 [SUPPLIER]
FeatureMerger_6
    ATTR_ACCUM_MODE = Merge Supplier
    ATTR_CONFLICT_RES = Use Requestor
    IGNORE_NULLS = No
    JOIN_KEYS = @Value(intrasis_archive) @Value(intrasis_archive) AUTO
    MERGE_TYPE = Attributes Only
    PROCESS_DUPS = NO
    REJECT_NULL_MISSING_KEYS = No
    SUPPLIERS_FIRST = No
archives_uuid_found_stickprov (reader OGCGEOPACKAGE_2)
    attributes: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
externa (reader OGCGEOPACKAGE_2)
    attributes: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
archives_check_uuid (reader OGCGEOPACKAGE_2)
    attributes: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
archives_check_geom (reader OGCGEOPACKAGE_2)
    attributes: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
empty (reader OGCGEOPACKAGE_2)
    attributes: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
GeometryRemover
    -> FeatureMerger_5 [REQUESTOR]
Note: jmr med proj som har någon geom utanför sv
FeatureMerger_5
    ATTR_ACCUM_MODE = Merge Supplier
    ATTR_CONFLICT_RES = Use Requestor
    IGNORE_NULLS = No
    JOIN_KEYS = @Value(intrasis_archive) @Value(master_site_archive) AUTO
    MERGE_TYPE = Attributes and Geometry
    PROCESS_DUPS = NO
    REJECT_NULL_MISSING_KEYS = No
    SUPPLIERS_FIRST = No
    MERGED -> FeatureMerger_3 [REQUESTOR]
    UNUSED_SUPPLIER -> FeatureMerger_4 [REQUESTOR]
Note: Merged- kollade av SL går inte att göra något åt / unmerged- har alla utom en uuid- det är ok den utan kollas upp
FeatureMerger_3
    ATTR_ACCUM_MODE = Merge Supplier
    ATTR_CONFLICT_RES = Use Requestor
    IGNORE_NULLS = No
    JOIN_KEYS = @Value(intrasis_archive) @Value(ia) AUTO
    MERGE_TYPE = Attributes and Geometry
    PROCESS_DUPS = NO
    REJECT_NULL_MISSING_KEYS = No
    SUPPLIERS_FIRST = No
    MERGED -> AttributeManager_7
    UNMERGED_REQUESTOR -> TestFilter_5
    UNUSED_SUPPLIER -> AttributeManager_8
AttributeManager_8
    ATTR_TABLE = SET_TO type_kix
    -> AttributeManager_7
Note: uuid not set fixas ej- / i princip tomma
TestFilter_5
    DEFAULT_VALUE = fixade
    PASSED_TEST_GROUP_OUTPUT = FIRST
    TEST_LIST:
      "BOOL_OP,AND,COMPOSITE_TEST,""""""1 AND 2"""""",TEST_CLAUSE,TEST master_UUID NOT_ATTRIBUTE_HAS_A_VALUE ""
      TEST UUID_andrat_av_uu NOT_ATTRIBUTE_HAS_A_VALUE """,uuid not set
    uuid not set -> AttributeManager_7
    fixade -> TestFilter_7
Note: sätter dessa som unfixed
AttributeManager_7
    ATTR_TABLE = SET_TO type_kix = unfixed
    -> FeatureMerger_4 [SUPPLIER]
Note: lägger till de 5 som vi hittat som inte är fixade
FeatureMerger_4
    ATTR_ACCUM_MODE = Merge Supplier
    ATTR_CONFLICT_RES = Use Supplier
    IGNORE_NULLS = No
    JOIN_KEYS = @Value(master_site_archive) @Value(master_site_archive) AUTO
    MERGE_TYPE = Attributes and Geometry
    PROCESS_DUPS = NO
    REJECT_NULL_MISSING_KEYS = No
    SUPPLIERS_FIRST = No
    MERGED -> TestFilter_7
    UNMERGED_REQUESTOR -> TestFilter_7
    UNUSED_SUPPLIER -> TestFilter_7
TestFilter_7
    DEFAULT_VALUE = <UNFILTERED>
    PASSED_TEST_GROUP_OUTPUT = FIRST
    TEST_LIST = "BOOL_OP,OR,COMPOSITE_TEST,""""""1"""""",TEST_CLAUSE,TEST @Value(type_kix) = empty",empty,"BOOL_OP,OR,COMPOSITE_TEST,""""""1"""""",TEST_CLAUSE,TEST @Value(type_kix) = extern",extern,"BOOL_OP,OR,COMPOSITE_TEST,""""""1"""""",TEST_CLAUSE,TEST @Value(type_kix) = unfixed",unfixed,"BOOL_OP,OR,COMPOSITE_TEST,""""""1"""""",TEST_CLAUSE,TEST @Value(type_kix) = uuid_found_stickprov",uuid_found_stickprov,"BOOL_OP,OR,COMPOSITE_TEST,""""""1"""""",TEST_CLAUSE,TEST @Value(type_kix) = check_uuid",check_uuid
    empty -> TestFilter_8
    extern -> SQLExecutor_3 [INITIATOR]
    extern -> TestFilter_8
    unfixed -> SQLExecutor [INITIATOR]
    unfixed -> TestFilter_8
    uuid_found_stickprov -> AttributeFilter_3
    uuid_found_stickprov -> TestFilter_8
    check_uuid -> AttributeFilter_3
    check_uuid -> TestFilter_8
    <UNFILTERED> -> AttributeFilter_3
    <UNFILTERED> -> AttributeManager_11
Note: sätter type_kix till manuell georef
AttributeManager_11
    ATTR_TABLE = SET_TO type_kix = manual_georef
    -> TestFilter_8
TestFilter_8
    DEFAULT_VALUE = <UNFILTERED>
    PASSED_TEST_GROUP_OUTPUT = FIRST
    TEST_LIST = "BOOL_OP,OR,COMPOSITE_TEST,""""""1"""""",TEST_CLAUSE,TEST 0 = 0",0 = 0
    0 = 0 -> AttributeManager_12
AttributeManager_12
    ATTR_TABLE:
      RENAME_SET_VALUE type_kix > Typ
      RENAME_SET_VALUE ok_kix > Kollat av UU
      RENAME_SET_VALUE _kommun > _kommun_spatial
      RENAME_SET_VALUE _lan > _lan_spatial
      RENAME_SET_VALUE _landskap > _landskap_spatial
      RENAME_SET_VALUE _socken_stad > _socken_stad_spatial
      REMOVE Status/kommentar
      REMOVE UUID status
      REMOVE Uppdrags-id status
      REMOVE Rapporttitel
      REMOVE Rapport finns var?
      REMOVE Åtgärd
      REMOVE pk
      REMOVE SiteId
      REMOVE Plats
      REMOVE Lst Dnr
      REMOVE Raä Dnr
      REMOVE Inventarienummer
      REMOVE Projektkod
      REMOVE Projektnamn
      REMOVE Projektledare
      REMOVE Uppdragsgivare
      REMOVE Exploateringstyp
      REMOVE Undersökningstyp
      REMOVE Slutdatum
      REMOVE Beskrivning
      REMOVE fid
      REMOVE id
      REMOVE lage
      REMOVE numOfFeature
      REMOVE geom_intrasisarchive
      REMOVE agg_feat
      REMOVE UUID_kix
      REMOVE master_H
      REMOVE master_col9
      REMOVE link_fornsok
      REMOVE _relationships.undersokningsomraden_id
      REMOVE _relationships.de9im
      REMOVE _relationships.pass__
      REMOVE _related_suppliers
      REMOVE project_info_intrasisarchive
      REMOVE datname
      REMOVE _traff_med_uo_id
      REMOVE traff_undersokningsomraden_id
      REMOVE intrasis_archive
      REMOVE ia
      REMOVE id_0
      REMOVE B
      REMOVE project_info_fid
      REMOVE project_info_id
      REMOVE intrasisarchive
      REMOVE Geoobjekt_manuellt_georefererade
      REMOVE Georeferering_precision
      REMOVE master__length_uppdrag_nr
    -> alla_intrasis_archive (writer OGCGEOPACKAGE_3)
    -> alla_intrasis_archive (writer XLSXW_1)
alla_intrasis_archive (writer OGCGEOPACKAGE_3)
    attributes: Typ text(200), Kollat av UU text(200), master_site_archive text(17), UUID_andrat_av_uu text(200), master_Uppdaterat UUID text(37), master_UUID text(37), master_uppdrag_nr int, master_kmr_uppdragsnummer int, master_kmr_id text(37), master_Kommentar text(685), master_uppdrag_ny text(200), project_info_Lst Dnr text, project_info_Raä Dnr text, project_info_Projektkod text, project_info_Projektnamn text, project_info_Projektledare text, project_info_Uppdragsgivare text, project_info_Undersökningstyp text, project_info_Slutdatum text, project_info_SiteId text, project_info_Exploateringstyp text, project_info_Beskrivning text, master_site_name text(54), project_info_pk mediumint, project_info_Plats text, project_info_Inventarienummer text, _kommun_spatial text, _kommun_fr_upp text, _lan_spatial text, _lan_fr_upp text,
      _landskap_spatial text, _socken_stad_spatial text, _socken_fr_upp text, _diarienummer_fr_upp text, _beslutande_myndighet_fr_upp text, _uppdragsnummer_fr_upp text, _utförande_org_fr_upp text, status text(6), C text, _relationships.pass{} text
alla_intrasis_archive (writer XLSXW_1)
    attributes: Typ string(200), Kollat av UU string(200), master_site_archive string(17), UUID_andrat_av_uu string(200), master_Uppdaterat UUID string(37), master_UUID string(37), master_uppdrag_nr number(20), master_kmr_uppdragsnummer number(20), master_kmr_id string(37), master_Kommentar string(685), master_uppdrag_ny string(200), project_info_Lst Dnr string(20), project_info_Raä Dnr string(20), project_info_Projektkod string(20), project_info_Projektnamn string(20), project_info_Projektledare string(20), project_info_Uppdragsgivare string(20), project_info_Undersökningstyp string(20), project_info_Slutdatum string(20), project_info_SiteId string(20), project_info_Exploateringstyp string(20), project_info_Beskrivning string(20), master_site_name string(54), project_info_pk number(20), project_info_Plats string(20), project_info_Inventarienummer string(20), _kommun_spatial string(20), _kommun_fr_upp string(20), _lan_spatial string(20), _lan_fr_upp string(20),
      _landskap_spatial string(20), _socken_stad_spatial string(20), _socken_fr_upp string(20), _diarienummer_fr_upp string(20), _beslutande_myndighet_fr_upp string(20), _uppdragsnummer_fr_upp string(20), _utförande_org_fr_upp string(20), status string(6), C string(20), _relationships.pass{} string(20)
TestFilter_4 [off]
    DEFAULT_VALUE = <UNFILTERED>
    PASSED_TEST_GROUP_OUTPUT = FIRST
    TEST_LIST = "BOOL_OP,OR,COMPOSITE_TEST,""""""1"""""",TEST_CLAUSE,TEST @Value(type_kix) = uuid_found_stickprov",@Value(type_kix) = uuid_found_stickprov,"BOOL_OP,OR,COMPOSITE_TEST,""""""1"""""",TEST_CLAUSE,TEST @Value(type_kix) = check_uuid",@Value(type_kix) = check_uuid,"BOOL_OP,OR,COMPOSITE_TEST,""""""1"""""",TEST_CLAUSE,TEST @Value(master_site_archive) = m2006935",@Value(master_site_archive) = m2006935,"BOOL_OP,OR,COMPOSITE_TEST,""""""1"""""",TEST_CLAUSE,TEST master_UUID ATTRIBUTE_HAS_A_VALUE """,master_UUID ATTRIBUTE_HAS_A_VALUE

Bookmark: fix
TestFilter
    DEFAULT_VALUE = <UNFILTERED>
    PASSED_TEST_GROUP_OUTPUT = FIRST
    TEST_LIST:
      "BOOL_OP,AND,COMPOSITE_TEST,""""""1 AND 2 AND 3 AND 4 AND 5 AND 6 AND 7 AND 8"""""",TEST_CLAUSE,TEST @Value(project_info_Lst Dnr) = @Value(Lst Dnr)
      TEST @Value(project_info_Projektledare) = @Value(Projektledare)
      TEST @Value(Projektkod) = @Value(project_info_Projektkod)
      TEST @Value(Projektnamn) = @Value(project_info_Projektnamn)
      TEST @Value(SiteId) = @Value(project_info_SiteId)
      TEST @Value(Slutdatum) = @Value(project_info_Slutdatum)
      TEST @Value(Undersökningstyp) = @Value(project_info_Undersökningstyp)
      TEST @Value(Uppdragsgivare) = @Value(project_info_Uppdragsgivare)",@Value(project_info_Lst Dnr) = @Value(Lst Dnr)
    @Value(project_info_Lst Dnr) = @Value(Lst Dnr) -> AttributeManager_3
    <UNFILTERED> -> AttributeManager_2
AttributeManager_2
    ATTR_TABLE:
      SET_TO project_info_Lst Dnr = @Value(Lst Dnr)
      SET_TO project_info_Projektnamn = @Value(Projektledare)
      SET_TO project_info_Uppdragsgivare = @Value(Uppdragsgivare)
      SET_TO project_info_Undersökningstyp = @Value(Undersökningstyp)
      SET_TO project_info_Slutdatum = @Value(Slutdatum)
    -> AttributeManager_3

Bookmark: 3006 bounds
Creator
    GEOMTYPE = Geometry Object
    NUM = 1
    CREATED -> EPSG:3006
EPSG:3006: AttributeManager
    ATTR_TABLE:
      SET_TO miny = 6090353.78
      SET_TO minx = 181896.33
      SET_TO maxy = 7689478.31
      SET_TO maxx = 1086312.94
    -> VertexCreator_2
VertexCreator_2
    CLOSE_LINES = Yes
    IGNORE_DUPLICATES = No
    MEASURE_TYPE = Continuous
    MISSING_VAL_MODE = Compute
    MODE_NAME = Add Point
    XVAL = @Value(minx)
    YVAL = @Value(miny)
    -> VertexCreator_3
VertexCreator_3
    CLOSE_LINES = Yes
    IGNORE_DUPLICATES = No
    MEASURE_TYPE = Continuous
    MISSING_VAL_MODE = Compute
    MODE_NAME = Add Point
    XVAL = @Value(maxx)
    YVAL = @Value(miny)
    -> VertexCreator
VertexCreator
    CLOSE_LINES = Yes
    IGNORE_DUPLICATES = No
    MEASURE_TYPE = Continuous
    MISSING_VAL_MODE = Compute
    MODE_NAME = Add Point
    XVAL = @Value(maxx)
    YVAL = @Value(maxy)
    -> VertexCreator_4
VertexCreator_4
    CLOSE_LINES = Yes
    IGNORE_DUPLICATES = No
    MEASURE_TYPE = Continuous
    MISSING_VAL_MODE = Compute
    MODE_NAME = Add Point
    XVAL = @Value(minx)
    YVAL = @Value(maxy)
    -> VertexCreator_5
VertexCreator_5
    CLOSE_LINES = Yes
    IGNORE_DUPLICATES = No
    MEASURE_TYPE = Continuous
    MISSING_VAL_MODE = Compute
    MODE_NAME = Add Point
    XVAL = @Value(minx)
    YVAL = @Value(miny)

Bookmark: kollar om någon av archives geom ligger inom sveriges gräns
Sverige_kl (reader OGCGEOPACKAGE_4)
    attributes: KOMMUNNAMN text(30), LANSNAMN text(30), arc_obj_ct double, Undersökta bpl lämningar double, Hus VT 2021 double, fid int,PrimaryKey
    -> Dissolver
Dissolver
    ACCUM_INPUT_ATTRS = Use Attributes From One Feature
    CLEANING_TOLERANCE = Automatic
    CONNECT_Z_MODE = First Wins
    DEAGGREGATE_INPUT = Yes
    AREA -> SpatialFilter_3 [Filter]
geom (reader OGCGEOPACKAGE_5)
    attributes: intrasis_archive text(200), id int,PrimaryKey
    -> Aggregator
Aggregator
    ACCUM_ATTRS_NAME = Drop Incoming Attributes
    AGGREGATE_TYPE = Homogeneous Collection (If Possible)
    GROUP_BY = intrasis_archive
    MODE = Geometry - Assemble One Level
    SEP = ,
    AGGREGATE -> TestFilter_6
Note: tar bort externa arkiv
TestFilter_6
    DEFAULT_VALUE = <UNFILTERED>
    PASSED_TEST_GROUP_OUTPUT = FIRST
    TEST_LIST = "BOOL_OP,OR,COMPOSITE_TEST,""""""1"""""",TEST_CLAUSE,CASE_INSENSITIVE_TEST @Value(intrasis_archive) BEGINS_WITH e",extern
    <UNFILTERED> -> SpatialFilter_3 [Candidate]
Note: någon geom innanför sveriges gräns
SpatialFilter_3
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS WITHIN CONTAINS
    USE_BOUNDING_BOX = No
    FAILED -> GeometryRemover

Bookmark: sakarias fil
intrasis_archive_geometry_check (reader XLSXR_1)
    attributes: status char(6), id_0 number(3,0), C string, intrasisarchive char(11), Status/kommentar char(138), UUID status char(55), Uppdrags-id status char(27), Rapporttitel char(352), Rapport finns var? char(50), Åtgärd char(63), pk number(3,0), SiteId char(11), Plats char(27), Lst Dnr char(15), Raä Dnr char(15), Inventarienummer char(13), Projektkod char(10), Projektnamn char(36), Projektledare char(24), Uppdragsgivare char(32), Exploateringstyp char(27), Undersökningstyp char(24), Slutdatum char(11), Beskrivning char(2060), fid number(2,0), id number(5,0), lage char(9), numOfFeature string, geom_intrasisarchive char(11), agg_feat number(6,0),
      UUID_kix char(37), master_site_name char(43), master_site_archive char(11), master_uppdrag_nr number(10,0), master_kmr_uppdragsnummer number(10,0), master_UUID char(37), master_kmr_id char(37), master_Uppdaterat UUID char(37), master_Kommentar char(179), master_H string, master_col9 char(70), master__length_uppdrag_nr number(2,0), link_fornsok char(77), master_uppdrag_ny number(10,0), _relationships.undersokningsomraden_id char(189), _relationships.de9im string, _relationships.pass{} string, _related_suppliers number(2,0), ok_kix char(6), project_info_intrasisarchive char(11), project_info_pk number(2,0), project_info_SiteId char(11), project_info_Plats char(27), project_info_Lst Dnr char(15), project_info_Raä Dnr char(15), project_info_Inventarienummer char(13), project_info_Projektkod char(10), project_info_Projektnamn char(36), project_info_Projektledare char(24), project_info_Uppdragsgivare char(32),
      project_info_Exploateringstyp char(27), project_info_Undersökningstyp char(24), project_info_Slutdatum char(11), project_info_Beskrivning char(2060), project_info_fid number(2,0), project_info_id number(5,0)
    -> FeatureMerger_7 [SUPPLIER]
Note: CSV: felaktiga_geom [CSV2] / från skaarias fil
CSV (reader CSV2_1)
    attributes: ia varchar(11)
    -> FeatureMerger_7 [REQUESTOR]
FeatureMerger_7
    ATTR_ACCUM_MODE = Merge Supplier
    ATTR_CONFLICT_RES = Use Requestor
    IGNORE_NULLS = No
    JOIN_KEYS = @Value(ia) @Value(intrasisarchive) AUTO
    MERGE_TYPE = Attributes Only
    PROCESS_DUPS = NO
    REJECT_NULL_MISSING_KEYS = No
    SUPPLIERS_FIRST = No
    MERGED -> FeatureMerger_3 [SUPPLIER]

Bookmark: fix epsg
SQLExecutor_3 [off]
    ATTR_IGNORE_NULLS = No
    COMBINE_ATTRS = Keep Initiator Attributes if Conflict
    COMBINE_GEOM = Initiator Geometry Only
    DATASET = @Value(master_site_archive)
    EXPOSED_ATTRIBUTE_LIST = Value
    FORMAT = POSTGIS
    OUTPUT_FEATURES_DISPLAY = Schema and Data Features
    POSTGIS_CREATE_FEATURE_TABLES_FROM_DATA = Yes
    POSTGIS_DISABLE_COLLECTION_SPLITTING = yes
    POSTGIS_HOST = uuc-srv390
    POSTGIS_PASSWORD = $(PASSWORD)
    POSTGIS_PORT = 5433
    POSTGIS_QUERY_FEATURE_TYPES_FOR_MERGE_FILTERS = Yes
    POSTGIS_READ_TIME_WITH_TIMEZONE = Yes
    POSTGIS_SSLMODE = prefer
    POSTGIS_USER_NAME = postgres
    POSTGIS_USE_TRUE_POSTGIS_TYPES = yes
    SQL_STATEMENT:
      SELECT av."Value"::integer FROM "Object" o JOIN "SysDefs" sd ON sd."SystemId" = 489
          JOIN "Attribute" a ON o."ObjectId" = a."ObjectId" AND a."MetaId" = sd."MetaId"
          JOIN "AttributeValue" av ON a."AttributeId" = av."AttributeId" WHERE o."ClassId" = 4
SQLExecutor [off]
    ATTR_IGNORE_NULLS = No
    COMBINE_ATTRS = Keep Initiator Attributes if Conflict
    COMBINE_GEOM = Initiator Geometry Only
    DATASET = @Value(master_site_archive)
    EXPOSED_ATTRIBUTE_LIST = Value
    FORMAT = POSTGIS
    OUTPUT_FEATURES_DISPLAY = Schema and Data Features
    POSTGIS_CREATE_FEATURE_TABLES_FROM_DATA = Yes
    POSTGIS_DISABLE_COLLECTION_SPLITTING = yes
    POSTGIS_HOST = uuc-srv390
    POSTGIS_PASSWORD = $(PASSWORD)
    POSTGIS_PORT = 5433
    POSTGIS_QUERY_FEATURE_TYPES_FOR_MERGE_FILTERS = Yes
    POSTGIS_READ_TIME_WITH_TIMEZONE = Yes
    POSTGIS_SSLMODE = prefer
    POSTGIS_USER_NAME = postgres
    POSTGIS_USE_TRUE_POSTGIS_TYPES = yes
    SQL_STATEMENT:
      SELECT av."Value"::integer FROM "Object" o JOIN "SysDefs" sd ON sd."SystemId" = 489
          JOIN "Attribute" a ON o."ObjectId" = a."ObjectId" AND a."MetaId" = sd."MetaId"
          JOIN "AttributeValue" av ON a."AttributeId" = av."AttributeId" WHERE o."ClassId" = 4
    RESULT -> AttributeManager_9 [off]
AttributeManager_9 [off]
    ATTR_TABLE = SET_TO Value = EPSG:@Value(Value)
    -> AttributeFilter [off]
AttributeFilter [off]
    ATTR_NAME = Value
    ATTR_VALUES = <Empty>,<Missing>,<Null>,<Unfiltered>,EPSG:3006,EPSG:3008,EPSG:3021,EPSG:4308
    EPSG:3006 -> Reprojector [off]
    EPSG:3008 -> Reprojector [off]
    EPSG:3021 -> Reprojector [off]
    EPSG:4308 -> Reprojector [off]
Note: prövade reproject on set epsg- funkade ej
Reprojector [off]
    DEST = EPSG:3006
    INTERPOLATION_TYPE_NAME = Nearest Neighbor
    RASTER_CELL_SIZE = Preserve Cells
    RASTER_TOLERANCE = 0.0
    SOURCE = @Value(Value)
AttributeFilter_3 [off]
    ATTR_NAME = master_site_archive
    ATTR_VALUES = <Empty>,<Missing>,<Null>,<Unfiltered>,s20021,uv2011244,v200020,v20005,o2009045,m2006935
    <EMPTY> -> SQLExecutor_2 [INITIATOR] [off]
    s20021 -> SQLExecutor_6 [INITIATOR] [off]
    uv2011244 -> SQLExecutor_6 [INITIATOR] [off]
    v200020 -> SQLExecutor_6 [INITIATOR] [off]
    v20005 -> SQLExecutor_6 [INITIATOR] [off]
    o2009045 -> SQLExecutor_6 [INITIATOR] [off]
    m2006935 -> SQLExecutor_6 [INITIATOR] [off]
SQLExecutor_2 [off]
    ATTR_IGNORE_NULLS = No
    COMBINE_ATTRS = Keep Initiator Attributes if Conflict
    COMBINE_GEOM = Initiator Geometry Only
    DATASET = @Value(master_site_archive)
    EXPOSED_ATTRIBUTE_LIST = Value
    FORMAT = POSTGIS
    OUTPUT_FEATURES_DISPLAY = Schema and Data Features
    POSTGIS_CREATE_FEATURE_TABLES_FROM_DATA = Yes
    POSTGIS_DISABLE_COLLECTION_SPLITTING = yes
    POSTGIS_HOST = uuc-srv390
    POSTGIS_PASSWORD = $(PASSWORD)
    POSTGIS_PORT = 5433
    POSTGIS_QUERY_FEATURE_TYPES_FOR_MERGE_FILTERS = Yes
    POSTGIS_READ_TIME_WITH_TIMEZONE = Yes
    POSTGIS_SSLMODE = prefer
    POSTGIS_USER_NAME = postgres
    POSTGIS_USE_TRUE_POSTGIS_TYPES = yes
    SQL_STATEMENT:
      SELECT av."Value"::integer FROM "Object" o JOIN "SysDefs" sd ON sd."SystemId" = 489
          JOIN "Attribute" a ON o."ObjectId" = a."ObjectId" AND a."MetaId" = sd."MetaId"
          JOIN "AttributeValue" av ON a."AttributeId" = av."AttributeId" WHERE o."ClassId" = 4
    RESULT -> AttributeManager_10 [off]
    <REJECTED> -> SQLExecutor_4 [INITIATOR] [off]
SQLExecutor_4 [off]
    ATTR_IGNORE_NULLS = No
    COMBINE_ATTRS = Keep Initiator Attributes if Conflict
    COMBINE_GEOM = Initiator Geometry Only
    DATASET = @Value(master_site_archive)
    EXPOSED_ATTRIBUTE_LIST = Value
    FORMAT = POSTGIS
    OUTPUT_FEATURES_DISPLAY = Schema and Data Features
    POSTGIS_CREATE_FEATURE_TABLES_FROM_DATA = Yes
    POSTGIS_DISABLE_COLLECTION_SPLITTING = yes
    POSTGIS_HOST = uuc-srv390
    POSTGIS_PASSWORD = $(PASSWORD)
    POSTGIS_PORT = 5433
    POSTGIS_QUERY_FEATURE_TYPES_FOR_MERGE_FILTERS = Yes
    POSTGIS_READ_TIME_WITH_TIMEZONE = Yes
    POSTGIS_SSLMODE = prefer
    POSTGIS_USER_NAME = postgres
    POSTGIS_USE_TRUE_POSTGIS_TYPES = yes
    SQL_STATEMENT:
      SELECT av."Value"::integer FROM "Object" o JOIN "SysDefs" sd ON sd."SystemId" = 489
          JOIN "Attribute" a ON o."ObjectId" = a."ObjectId" AND a."MetaId" = sd."MetaId"
          JOIN "AttributeValue" av ON a."AttributeId" = av."AttributeId" WHERE o."ClassId" = 4
    RESULT -> AttributeManager_10 [off]
AttributeManager_10 [off]
    ATTR_TABLE = SET_TO Value = EPSG:@Value(Value)
    -> SQLExecutor_6 [INITIATOR] [off]
SQLExecutor_6 [off]
    ATTR_IGNORE_NULLS = No
    COMBINE_ATTRS = Keep Initiator Attributes if Conflict
    COMBINE_GEOM = Initiator Geometry Only
    DATASET = @Value(master_site_archive)
    EXPOSED_ATTRIBUTE_LIST = Value
    FORMAT = POSTGIS
    OUTPUT_FEATURES_DISPLAY = Schema and Data Features
    POSTGIS_CREATE_FEATURE_TABLES_FROM_DATA = Yes
    POSTGIS_DISABLE_COLLECTION_SPLITTING = yes
    POSTGIS_HOST = uuc-srv390
    POSTGIS_PASSWORD = $(PASSWORD)
    POSTGIS_PORT = 5433
    POSTGIS_QUERY_FEATURE_TYPES_FOR_MERGE_FILTERS = Yes
    POSTGIS_READ_TIME_WITH_TIMEZONE = Yes
    POSTGIS_SSLMODE = prefer
    POSTGIS_USER_NAME = postgres
    POSTGIS_USE_TRUE_POSTGIS_TYPES = yes
    SQL_STATEMENT:
      SELECT av."Value"::integer FROM "Object" o JOIN "SysDefs" sd ON sd."SystemId" = 489
          JOIN "Attribute" a ON o."ObjectId" = a."ObjectId" AND a."MetaId" = sd."MetaId"
          JOIN "AttributeValue" av ON a."AttributeId" = av."AttributeId" WHERE o."ClassId" = 4
    <SCHEMA> -> SQLExecutor_5 [INITIATOR] [off]
SQLExecutor_5 [off]
    ATTR_IGNORE_NULLS = No
    COMBINE_ATTRS = Keep Initiator Attributes if Conflict
    COMBINE_GEOM = Initiator Geometry Only
    DATASET = @Value(master_site_archive)
    EXPOSED_ATTRIBUTE_LIST = Value
    FORMAT = POSTGIS
    OUTPUT_FEATURES_DISPLAY = Schema and Data Features
    POSTGIS_CREATE_FEATURE_TABLES_FROM_DATA = Yes
    POSTGIS_DISABLE_COLLECTION_SPLITTING = yes
    POSTGIS_HOST = uuc-srv390
    POSTGIS_PASSWORD = $(PASSWORD)
    POSTGIS_PORT = 5433
    POSTGIS_QUERY_FEATURE_TYPES_FOR_MERGE_FILTERS = Yes
    POSTGIS_READ_TIME_WITH_TIMEZONE = Yes
    POSTGIS_SSLMODE = prefer
    POSTGIS_USER_NAME = postgres
    POSTGIS_USE_TRUE_POSTGIS_TYPES = yes
    SQL_STATEMENT:
      update  "AttributeValue"  SET "Value"='3006'
      where "AttributeValueId"= (
      Select av."AttributeValueId"
      from  "SysDefs" sd,  "Attribute" a, "Object" o , "AttributeValue" av
      where
      	sd."SystemId" = 489
          And  o."ObjectId" = a."ObjectId"
      	AND a."MetaId" = sd."MetaId"
          AND  a."AttributeId" = av."AttributeId"
      	And o."ClassId" = 4 )
AttributeFilter_2 [off]
    ATTR_NAME = Value
    ATTR_VALUES = <Empty>,<Missing>,<Null>,<Unfiltered>,EPSG:0,EPSG:3006,EPSG:3008,EPSG:3019,EPSG:3021
