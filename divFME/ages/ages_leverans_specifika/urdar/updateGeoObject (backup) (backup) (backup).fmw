FME workspace updateGeoObject (backup) (backup) (backup).fmw

Parameters:
- DestDataset_POSTGIS_1 = v200020   # Database
- HOST_POSTGIS = uuc-srv390   # Host
- PORT_POSTGIS = 5433   # Port
- USER_NAME_POSTGIS = postgres   # Username
- PASSWORD_POSTGIS =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   # Password
- SourceDataset_OGCGEOPACKAGE = C:\Users\krima354\Box\Urdar\Geom_fixed_SL_20231208\v200020_geom_fixed.gpkg   # GeoPackage File

Readers:
- POSTGIS_2: POSTGIS from $(DestDataset_POSTGIS_1) in EPSG:3006
- OGCGEOPACKAGE_1: OGCGEOPACKAGE from $(SourceDataset_OGCGEOPACKAGE)

Writers:
- POSTGIS_1: POSTGIS to $(DestDataset_POSTGIS_1)

GeoObject (reader OGCGEOPACKAGE_1)
    attributes: id int, ObjectId mediumint, MetaId mediumint, SymbolId mediumint, the_raster text(200), fid int,PrimaryKey
GeoObject (reader POSTGIS_2)
    attributes: ObjectId int4, MetaId int4, SymbolId int4, the_raster raster
Reprojector
    DEST = EPSG:3006
    INTERPOLATION_TYPE_NAME = Nearest Neighbor
    RASTER_CELL_SIZE = Preserve Cells
    RASTER_TOLERANCE = 0.0
GeoObject (writer POSTGIS_1)
    attributes: ObjectId int4, MetaId int4, SymbolId int4
