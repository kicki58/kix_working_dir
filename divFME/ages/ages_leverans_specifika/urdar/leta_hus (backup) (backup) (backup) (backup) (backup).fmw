FME workspace leta_hus (backup) (backup) (backup) (backup) (backup).fmw

Parameters:
- SourceDataset_POSTGRES_1 = A2010_172_RAA52   # Database
- HOST_POSTGRES = localhost   # Host
- PORT_POSTGRES = 5432   # Port
- DestDataset_OGCGEOPACKAGE = C:\Users\krima354\Work Folders\Documents\kicki_arbetsfiler\slask\hitta_hus.gpkg   # GeoPackage File

Readers:
- POSTGRES_1: POSTGRES from $(SourceDataset_POSTGRES_1)

Writers:
- OGCGEOPACKAGE_1: OGCGEOPACKAGE to $(DestDataset_OGCGEOPACKAGE)

ClassDef (reader POSTGRES_1)
    attributes: MetaId int4, CanAddSubclass bool, SpecialRegIsActive bool, InfoGroupDefId int4, IsUserEditable bool, GetHighId bool, ShowAsObjectInfo int4, SubClassDesignatorId int4, ClassOrder int2
    -> FeatureMerger_3 [REQUESTOR]
Definition (reader POSTGRES_1)
    attributes: MetaId int4, VersionReferenceId int4, Name varchar(50), Description varchar(100), ToolTip varchar(50), Help text, ExternalId int4, IsSystemDefinition bool
    -> FeatureMerger_3 [SUPPLIER]
    -> FeatureMerger_4 [SUPPLIER]
FeatureMerger_3
    ATTR_ACCUM_MODE = Merge Supplier
    ATTR_CONFLICT_RES = Use Requestor
    IGNORE_NULLS = No
    JOIN_KEYS = @Value(MetaId) @Value(MetaId) AUTO
    MERGE_TYPE = Attributes Only
    PROCESS_DUPS = NO
    REJECT_NULL_MISSING_KEYS = No
    SUPPLIERS_FIRST = No
    MERGED -> AttributeKeeper
AttributeKeeper
    CREATE_BULK_MODE_FEATURES = NO
    KEEP_ATTRS = MetaId,Name,ToolTip
    -> BulkAttributeRenamer_2
BulkAttributeRenamer_2
    ATTRCHOICE = All Attributes
    MODE_CHOICE = RENAME
    PATTERN_ACTION_DISP = ADDPREFIX
    REPLACE_STR = class_def_
    -> FeatureMerger [SUPPLIER]
Attribute (reader POSTGRES_1)
    attributes: AttributeId int4, MetaId int4, ObjectId int4, Label varchar(50)
    -> FeatureMerger_5 [REQUESTOR]
AttributeDef (reader POSTGRES_1)
    attributes: MetaId int4, Label varchar(30), MultipleAllowed bool, FreeValueAllowed bool, NotNull bool, DataType varchar(35), Unit varchar(20), Length int2
    -> FeatureMerger_5 [SUPPLIER]
FeatureMerger_5
    ATTR_ACCUM_MODE = Merge Supplier
    ATTR_CONFLICT_RES = Use Requestor
    IGNORE_NULLS = No
    JOIN_KEYS = @Value(MetaId) @Value(MetaId) AUTO
    MERGE_TYPE = Attributes Only
    PROCESS_DUPS = NO
    REJECT_NULL_MISSING_KEYS = No
    SUPPLIERS_FIRST = No
    MERGED -> FeatureMerger_6 [REQUESTOR]
AttributeValue (reader POSTGRES_1)
    attributes: AttributeValueId int4, AttributeId int4, Value varchar(260), Unit varchar(30)
    -> FeatureMerger_6 [SUPPLIER]
FeatureMerger_6
    ATTR_ACCUM_MODE = Merge Supplier
    ATTR_CONFLICT_RES = Use Requestor
    IGNORE_NULLS = No
    JOIN_KEYS = @Value(AttributeId) @Value(AttributeId) AUTO
    MERGE_TYPE = Attributes Only
    PROCESS_DUPS = NO
    REJECT_NULL_MISSING_KEYS = No
    SUPPLIERS_FIRST = No
    MERGED -> AttributeKeeper_3
    UNMERGED_REQUESTOR -> FeatureMerger_7 [REQUESTOR]
FreeText (reader POSTGRES_1)
    attributes: AttributeId int4, Text text, converted_text text
    -> FeatureMerger_7 [SUPPLIER]
FeatureMerger_7
    ATTR_ACCUM_MODE = Merge Supplier
    ATTR_CONFLICT_RES = Use Requestor
    IGNORE_NULLS = No
    JOIN_KEYS = @Value(AttributeId) @Value(AttributeId) AUTO
    MERGE_TYPE = Attributes Only
    PROCESS_DUPS = NO
    REJECT_NULL_MISSING_KEYS = No
    SUPPLIERS_FIRST = No
    MERGED -> AttributeKeeper_3
    UNMERGED_REQUESTOR -> AttributeKeeper_3
AttributeKeeper_3
    CREATE_BULK_MODE_FEATURES = NO
    KEEP_ATTRS = Label,ObjectId,Unit,Value,converted_text
    -> BulkAttributeRenamer_4
BulkAttributeRenamer_4
    ATTRCHOICE = All Attributes
    MODE_CHOICE = RENAME
    PATTERN_ACTION_DISP = ADDPREFIX
    REPLACE_STR = attr_
    -> FeatureMerger_8 [REQUESTOR]
SubClassDef (reader POSTGRES_1)
    attributes: MetaId int4, ClassId int4
    -> FeatureMerger_4 [REQUESTOR]
FeatureMerger_4
    ATTR_ACCUM_MODE = Merge Supplier
    ATTR_CONFLICT_RES = Use Requestor
    IGNORE_NULLS = No
    JOIN_KEYS = @Value(MetaId) @Value(MetaId) AUTO
    MERGE_TYPE = Attributes Only
    PROCESS_DUPS = NO
    REJECT_NULL_MISSING_KEYS = No
    SUPPLIERS_FIRST = No
    MERGED -> AttributeKeeper_2
AttributeKeeper_2
    CREATE_BULK_MODE_FEATURES = NO
    KEEP_ATTRS = MetaId,Name,ToolTip
    -> BulkAttributeRenamer_3
BulkAttributeRenamer_3
    ATTRCHOICE = All Attributes
    MODE_CHOICE = RENAME
    PATTERN_ACTION_DISP = ADDPREFIX
    REPLACE_STR = sub_class_def_
    -> FeatureMerger_2 [SUPPLIER]
Object (reader POSTGRES_1)
    attributes: ObjectId int4, ClassId int4, SubClassId int4, PublicId int4, Name varchar(50), SiteId int4, Origin int4
    -> FeatureMerger_8 [SUPPLIER]
FeatureMerger_8
    ATTR_ACCUM_MODE = Merge Supplier
    ATTR_CONFLICT_RES = Use Requestor
    IGNORE_NULLS = No
    JOIN_KEYS = @Value(attr_ObjectId) @Value(ObjectId) AUTO
    MERGE_TYPE = Attributes Only
    PROCESS_DUPS = NO
    REJECT_NULL_MISSING_KEYS = No
    SUPPLIERS_FIRST = No
    MERGED -> FeatureMerger [REQUESTOR]
FeatureMerger
    ATTR_ACCUM_MODE = Merge Supplier
    ATTR_CONFLICT_RES = Use Requestor
    IGNORE_NULLS = No
    JOIN_KEYS = @Value(ClassId) @Value(class_def_MetaId) AUTO
    MERGE_TYPE = Attributes Only
    PROCESS_DUPS = NO
    REJECT_NULL_MISSING_KEYS = No
    SUPPLIERS_FIRST = No
    MERGED -> FeatureMerger_2 [REQUESTOR]
    UNMERGED_REQUESTOR -> FeatureMerger_2 [REQUESTOR]
FeatureMerger_2
    ATTR_ACCUM_MODE = Merge Supplier
    ATTR_CONFLICT_RES = Use Requestor
    IGNORE_NULLS = No
    JOIN_KEYS = @Value(SubClassId) @Value(sub_class_def_MetaId) AUTO
    MERGE_TYPE = Attributes Only
    PROCESS_DUPS = NO
    REJECT_NULL_MISSING_KEYS = No
    SUPPLIERS_FIRST = No
    MERGED -> Tester
    UNMERGED_REQUESTOR -> Tester
Tester
    BOOL_OP = OR
    TEST_CLAUSE:
      CASE_INSENSITIVE_TEST @Value(attr_converted_text) CONTAINS hus
      CASE_INSENSITIVE_TEST @Value(attr_Label) CONTAINS hus
      CASE_INSENSITIVE_TEST @Value(attr_Value) CONTAINS hus
      CASE_INSENSITIVE_TEST @Value(class_def_Name) CONTAINS hus
      CASE_INSENSITIVE_TEST @Value(Name) CONTAINS hus
      CASE_INSENSITIVE_TEST @Value(sub_class_def_Name) CONTAINS hus
      CASE_INSENSITIVE_TEST @Value(sub_class_def_ToolTip) CONTAINS hus
    TEST_MODE = CASE_INSENSITIVE_TEST
    PASSED -> ListBuilder
ListBuilder
    GROUP_BY = attr_ObjectId
    LIST_ATTRS_TO_INCLUDE = attr_Label class_def_Name class_def_ToolTip sub_class_def_Name sub_class_def_ToolTip attr_converted_text attr_Value Name
    LIST_NAME = _list
    -> ListDuplicateRemover
ListDuplicateRemover
    SRC_LIST = _list{}.attr_converted_text
    -> ListConcatenator
ListConcatenator
    DROP_EMPTY_PARTS = Yes
    LIST_ATTR = _list{}.attr_converted_text
    SEP = " , "
    VAL_ATTR = _concat_attr_converted_text
    -> ListDuplicateRemover_2
ListDuplicateRemover_2
    SRC_LIST = _list{}.attr_Label
    -> ListConcatenator_2
ListConcatenator_2
    DROP_EMPTY_PARTS = Yes
    LIST_ATTR = _list{}.attr_Label
    SEP = " , "
    VAL_ATTR = _concat_attr_Label
    -> ListDuplicateRemover_3
ListDuplicateRemover_3
    SRC_LIST = _list{}.attr_Value
    -> ListConcatenator_3
ListConcatenator_3
    DROP_EMPTY_PARTS = Yes
    LIST_ATTR = _list{}.attr_Value
    SEP = " , "
    VAL_ATTR = _concat_attr_Value
    -> ListDuplicateRemover_4
ListDuplicateRemover_4
    SRC_LIST = _list{}.class_def_Name
    -> ListConcatenator_4
ListConcatenator_4
    DROP_EMPTY_PARTS = Yes
    LIST_ATTR = _list{}.class_def_Name
    SEP = " , "
    VAL_ATTR = _concat_class_def_name
    -> ListDuplicateRemover_5
ListDuplicateRemover_5
    SRC_LIST = _list{}.class_def_ToolTip
    -> ListConcatenator_5
ListConcatenator_5
    DROP_EMPTY_PARTS = Yes
    LIST_ATTR = _list{}.class_def_ToolTip
    SEP = " , "
    VAL_ATTR = _concat_class_def_ToolTip
    -> ListDuplicateRemover_6
ListDuplicateRemover_6
    SRC_LIST = _list{}.Name
    -> ListConcatenator_6
ListConcatenator_6
    DROP_EMPTY_PARTS = Yes
    LIST_ATTR = _list{}.Name
    SEP = " , "
    VAL_ATTR = _concat_name
    -> ListDuplicateRemover_7
ListDuplicateRemover_7
    SRC_LIST = _list{}.sub_class_def_Name
    -> ListConcatenator_7
ListConcatenator_7
    DROP_EMPTY_PARTS = Yes
    LIST_ATTR = _list{}.sub_class_def_Name
    SEP = " , "
    VAL_ATTR = _concat_sub_classname
    -> ListDuplicateRemover_8
ListDuplicateRemover_8
    SRC_LIST = _list{}.sub_class_def_ToolTip
    -> ListConcatenator_8
ListConcatenator_8
    DROP_EMPTY_PARTS = Yes
    LIST_ATTR = _list{}.sub_class_def_ToolTip
    SEP = " , "
    VAL_ATTR = _concat_sub_def_ToolTip
    -> AttributeKeeper_4
AttributeKeeper_4
    CREATE_BULK_MODE_FEATURES = NO
    KEEP_ATTRS = _concat_attr_Label,_concat_attr_Value,_concat_attr_converted_text,_concat_class_def_ToolTip,_concat_class_def_name,_concat_name,_concat_sub_classname,_concat_sub_def_ToolTip,attr_ObjectId
    -> AttributeManager
AttributeManager
    -> hus_fran_urdar (writer OGCGEOPACKAGE_1)
hus_fran_urdar (writer OGCGEOPACKAGE_1)
    attributes: attr_ObjectId mediumint, _concat_attr_converted_text text, _concat_attr_Label text, _concat_attr_Value text, _concat_class_def_name text, _concat_class_def_ToolTip text, _concat_name text, _concat_sub_classname text, _concat_sub_def_ToolTip text
