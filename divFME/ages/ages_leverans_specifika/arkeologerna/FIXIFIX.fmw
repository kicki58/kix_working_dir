FME workspace FIXIFIX.fmw

Parameters:
- SourceDataset_OGCGEOPACKAGE = C:\ny_slask\arkeologerna\jmfr4.gpkg   # GeoPackage File
- SourceDataset_PATH = C:\ny_slask\arkeologerna   # INCLUDE_WEB_BROWSER Source Folder and File Pathnames Folder
- SourceDataset_OGCGEOPACKAGE_3 = C:\ny_slask\arkeologerna\aggregated_reprojected.gpkg   # GeoPackage File
- DestDataset_OGCGEOPACKAGE = C:\ny_slask\arkeologerna\arkeologerna_check_uo4.gpkg   # GeoPackage File

Readers:
- OGCGEOPACKAGE_1: OGCGEOPACKAGE from $(SourceDataset_OGCGEOPACKAGE)
- PATH_1: PATH from $(SourceDataset_PATH)
- OGCGEOPACKAGE_2: OGCGEOPACKAGE from $(SourceDataset_OGCGEOPACKAGE_3)

Writers:
- OGCGEOPACKAGE_3: OGCGEOPACKAGE to $(DestDataset_OGCGEOPACKAGE)

kollade_mot_uo_deagg (reader OGCGEOPACKAGE_1)
    attributes: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
att_kolla_upp_deagg (reader OGCGEOPACKAGE_1)
    attributes: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
dubletter_lst_nr_5st (reader OGCGEOPACKAGE_1)
    attributes: uppdragsnummer text(9), diarienummer text(255), dublett_diarienummer text(255), arkeologenrna_lst dnr text, dublett_arkeologenrna_path_rootname text, dublett_arkeologenrna_lst dnr text, arkeologenrna_path_rootname text, dublett_url text(255), url text(255), id int,PrimaryKey
    -> Tester
Tester
    BOOL_OP = OR
    TEST_CLAUSE = TEST diarienummer ATTRIBUTE_HAS_A_VALUE ""
    TEST_MODE = TEST
    FAILED -> AttributeManager
AttributeManager
    ATTR_TABLE:
      RENAME_SET_VALUE dublett_arkeologenrna_path_rootname > intrasis_name (buffer)
      RENAME_SET_VALUE uppdragsnummer > hittad_uo (varchar(9))
      REMOVE diarienummer (varchar(255))
      REMOVE dublett_diarienummer (varchar(255))
      REMOVE arkeologenrna_lst dnr (buffer)
      REMOVE dublett_arkeologenrna_lst dnr (buffer)
      REMOVE dublett_url (varchar(255))
      REMOVE url (varchar(255))
      REMOVE id (int64)
      REMOVE arkeologenrna_path_rootname (buffer)
    -> Tester_2
att_kolla_upp (reader OGCGEOPACKAGE_1)
    attributes: intrasis_name text, hittad_uo text(200), _upp text, _url text, pk mediumint, siteid text, plats text, lst dnr text, raä dnr text, inventarienummer text, projektkod text, projektnamn text, projektledare text, uppdragsgivare text, exploateringstyp text, undersökningstyp text, slutdatum text, beskrivning text, object_id mediumint, class text, subclass text, symbolid mediumint, geoobjectid mediumint, spatial_type text, _relationships.diarienummer text, arkeologenrna_path_unix text, arkeologenrna_path_windows text, arkeologenrna_path_rootname text, arkeologenrna_path_filename text, arkeologenrna_path_extension text,
      arkeologenrna_path_directory_unix text, arkeologenrna_path_directory_windows text, arkeologenrna_path_type text(10), arkeologenrna_uppdragsnummer text, arkeologenrna_u-nummer text, arkeologenrna_lst dnr text, uppdragsnummer text(9), beslutande_myndighet text(255), beslutsdatum date, diarienummer text(255), uppdragstyp text(255), utforande_organisation text(255), nollresultat text(9), url text(255), status text(255), lan text, kommun text, socken text, id int,PrimaryKey
    -> AttributeManager_3
AttributeManager_3
    ATTR_TABLE:
      SET_TO from_arkeologerna (varchar(16)) = saknas-handjagad
      REMOVE arkeologenrna_path_unix (buffer)
      REMOVE arkeologenrna_path_windows (buffer)
      REMOVE arkeologenrna_path_rootname (buffer)
      REMOVE arkeologenrna_path_filename (buffer)
      REMOVE arkeologenrna_path_extension (buffer)
      REMOVE arkeologenrna_path_directory_unix (buffer)
      REMOVE arkeologenrna_path_directory_windows (buffer)
      REMOVE arkeologenrna_path_type (varchar(10))
      REMOVE arkeologenrna_uppdragsnummer (buffer)
      REMOVE arkeologenrna_u-nummer (buffer)
      REMOVE arkeologenrna_lst dnr (buffer)
      REMOVE uppdragsnummer (varchar(9))
      REMOVE beslutande_myndighet (varchar(255))
      REMOVE beslutsdatum (date)
      REMOVE diarienummer (varchar(255))
      REMOVE uppdragstyp (varchar(255))
      REMOVE utforande_organisation (varchar(255))
      REMOVE nollresultat (varchar(9))
      REMOVE url (varchar(255))
      REMOVE status (varchar(255))
      REMOVE lan (buffer)
      REMOVE kommun (buffer)
      REMOVE socken (buffer)
      REMOVE id (int64)
      REMOVE object_id (int32)
      REMOVE class (buffer)
      REMOVE subclass (buffer)
      REMOVE symbolid (int32)
      REMOVE geoobjectid (int32)
      REMOVE spatial_type (buffer)
    -> Tester_2
kollade_mot_uo (reader OGCGEOPACKAGE_1)
    attributes: intrasis_name text, hittad_uo text(200), hittad_url text(200), verifierad text(200), _upp text, _url text, from_arkelogerna text(16), pk mediumint, siteid text, plats text, lst dnr text, raä dnr text, inventarienummer text, projektkod text, projektnamn text, projektledare text, uppdragsgivare text, exploateringstyp text, undersökningstyp text, slutdatum text, beskrivning text, object_id mediumint, class text, subclass text, symbolid mediumint, geoobjectid mediumint, spatial_type text, _relationships.uppdragsnummer text, _relationships.diarienummer text, _relationships.url text,
      _relationships.de9im text, _relationships.pass{} text, _related_suppliers int, arkeologenrna_path_unix text, arkeologenrna_path_windows text, arkeologenrna_path_rootname text, arkeologenrna_path_filename text, arkeologenrna_path_extension text, arkeologenrna_path_directory_unix text, arkeologenrna_path_directory_windows text, arkeologenrna_path_type text(10), arkeologenrna_uppdragsnummer text, arkeologenrna_u-nummer text, arkeologenrna_lst dnr text, _list_index int, uppdragsnummer text(9), beslutande_myndighet text(255), beslutsdatum date, diarienummer text(255), uppdragstyp text(255), utforande_organisation text(255), nollresultat text(9), url text(255), status text(255), lan text, kommun text, socken text, id int,PrimaryKey
    -> AttributeManager_2
AttributeManager_2
    ATTR_TABLE:
      RENAME_SET_VALUE from_arkelogerna > from_arkeologerna (varchar(16))
      REMOVE _relationships.de9im (buffer)
      REMOVE _relationships.pass{} (buffer)
      REMOVE _related_suppliers (int64)
      REMOVE arkeologenrna_path_unix (buffer)
      REMOVE arkeologenrna_path_windows (buffer)
      REMOVE arkeologenrna_path_rootname (buffer)
      REMOVE arkeologenrna_path_filename (buffer)
      REMOVE arkeologenrna_path_extension (buffer)
      REMOVE arkeologenrna_path_directory_unix (buffer)
      REMOVE arkeologenrna_path_directory_windows (buffer)
      REMOVE arkeologenrna_path_type (varchar(10))
      REMOVE arkeologenrna_uppdragsnummer (buffer)
      REMOVE arkeologenrna_u-nummer (buffer)
      REMOVE arkeologenrna_lst dnr (buffer)
      REMOVE _list_index (int64)
      REMOVE uppdragsnummer (varchar(9))
      REMOVE beslutande_myndighet (varchar(255))
      REMOVE beslutsdatum (date)
      REMOVE diarienummer (varchar(255))
      REMOVE uppdragstyp (varchar(255))
      REMOVE utforande_organisation (varchar(255))
      REMOVE nollresultat (varchar(9))
      REMOVE url (varchar(255))
      REMOVE status (varchar(255))
      REMOVE lan (buffer)
      REMOVE kommun (buffer)
      REMOVE socken (buffer)
      REMOVE id (int64)
      REMOVE object_id (int32)
      REMOVE class (buffer)
      REMOVE subclass (buffer)
      REMOVE symbolid (int32)
      REMOVE geoobjectid (int32)
      REMOVE spatial_type (buffer)
    -> Tester_2
Tester_2
    BOOL_OP = OR
    TEST_CLAUSE = TEST 1 = 1
    TEST_MODE = TEST
    PASSED -> DuplicateFilter
DuplicateFilter
    INPUT_ORDERED_CHOICE_LOOKUP = NO
    KEYATTR = intrasis_name
    INPUT_ORDERED_CHOICE = No
    UNIQUE -> FeatureMerger [SUPPLIER]
PATH (reader PATH_1)
    attributes: path_unix buffer, path_windows buffer, path_rootname buffer, path_filename buffer, path_extension buffer, path_directory_unix buffer, path_directory_windows buffer, path_type char(10)
    -> AttributeFilter_2
AttributeFilter_2
    ATTR_NAME = path_rootname
    ATTR_VALUES = <Empty>,<Missing>,<Null>,<Unfiltered>,agg_uppdragsnummer,aggregated_intrasis,aggregated,aggregated_reprojected,jmfr4
    <UNFILTERED> -> FeatureMerger [REQUESTOR]
FeatureMerger
    ATTR_ACCUM_MODE = Merge Supplier
    ATTR_CONFLICT_RES_LOOKUP = REQUESTOR_IF_CONFLICT
    IGNORE_NULLS = No
    JOIN_KEYS = @Value(path_rootname) @Value(intrasis_name) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> Tester_3
    UNMERGED_REQUESTOR -> FeatureMerger_2 [REQUESTOR]
project_information (reader OGCGEOPACKAGE_2)
    attributes: intrasis_name text, pk mediumint, siteid text, plats text, lst dnr text, raä dnr text, inventarienummer text, projektkod text, projektnamn text, projektledare text, uppdragsgivare text, exploateringstyp text, undersökningstyp text, slutdatum text, beskrivning text, id int,PrimaryKey
    -> AttributeRemover
    -> FeatureMerger_2 [SUPPLIER]
FeatureMerger_2
    ATTR_ACCUM_MODE = Merge Supplier
    ATTR_CONFLICT_RES_LOOKUP = REQUESTOR_IF_CONFLICT
    IGNORE_NULLS = No
    JOIN_KEYS = @Value(path_rootname) @Value(intrasis_name) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> AttributeManager_4
AttributeManager_4
    ATTR_TABLE:
      SET_TO from_arkeologerna (varchar(15)) = ej kollad av uu
      REMOVE path_unix (buffer)
      REMOVE path_windows (buffer)
      REMOVE path_rootname (buffer)
      REMOVE path_filename (buffer)
      REMOVE path_extension (buffer)
      REMOVE path_directory_unix (buffer)
      REMOVE path_directory_windows (buffer)
      REMOVE path_type (varchar(10))
    -> Tester_3
Tester_3
    BOOL_OP = OR
    TEST_CLAUSE = TEST 1 = 1
    TEST_MODE = TEST
    PASSED -> AttributeManager_5
AttributeManager_5
    ATTR_TABLE:
      REMOVE path_unix (buffer)
      REMOVE path_windows (buffer)
      REMOVE path_rootname (buffer)
      REMOVE path_filename (buffer)
      REMOVE path_extension (buffer)
      REMOVE path_directory_unix (buffer)
      REMOVE path_directory_windows (buffer)
      REMOVE path_type (varchar(10))
    -> FeatureMerger_3 [REQUESTOR]
AttributeRemover
    REMOVE_ATTRS = beskrivning,exploateringstyp,id,inventarienummer,lst dnr,pk,plats,projektkod,projektledare,projektnamn,raä dnr,slutdatum,undersökningstyp,uppdragsgivare,siteid
    -> FeatureMerger_3 [SUPPLIER]
FeatureMerger_3
    JOIN_KEYS = @Value(intrasis_name) @Value(intrasis_name) AUTO
    MERGE_TYPE_VAL = GEOM_BUILD
    PROCESS_DUPS = NO
    REJECT_NULL_MISSING_KEYS = No
    SUPPLIERS_FIRST = No
    MERGE_TYPE = Geometry
    MERGED -> intrasis_gpkg (writer OGCGEOPACKAGE_3)
intrasis_gpkg (writer OGCGEOPACKAGE_3)
    attributes: intrasis_name text, hittad_uo text(20), verifierad text(200), from_arkeologerna text(16), hittad_url text(200), pk mediumint, siteid text, plats text, lst dnr text, raä dnr text, inventarienummer text, projektkod text, projektnamn text, projektledare text, uppdragsgivare text, exploateringstyp text, undersökningstyp text, slutdatum text, beskrivning text, id int, _upp text, _url text, _relationships.uppdragsnummer text, _relationships.diarienummer text, _relationships.url text
