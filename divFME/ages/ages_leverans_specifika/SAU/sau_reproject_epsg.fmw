FME workspace sau_reproject_epsg.fmw

Parameters:
- HOST_POSTGISserver = uuc-srv390.user.uu.se   # Server
- Source_Dest_Dataset_POSTGIS_2 = sau2011lager4096   # Database
- USER_NAME_POSTGIS_2 = postgres   # Username
- PASSWORD_2 =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   # Password
- PORT_POSTGIS_2 = 5432   # Port
- SOURCE = EPSG:3010   # EnableReadFromFeature:Yes Source Coordinate System

Readers:
- POSTGIS_1: POSTGIS from $(Source_Dest_Dataset_POSTGIS_2)

Writers:
- POSTGIS_2: POSTGIS to $(Source_Dest_Dataset_POSTGIS_2)

GeoObject (reader POSTGIS_1)
    attributes: ObjectId int4, MetaId int4, SymbolId int4, the_raster raster
    -> TestFilter
TestFilter
    DEFAULT_VALUE = <UNFILTERED>
    PASSED_TEST_GROUP_OUTPUT = FIRST
    TEST_LIST = "BOOL_OP,OR,COMPOSITE_TEST,""""""1"""""",TEST_CLAUSE,TEST $(SOURCE) = EPSG:3022",EPSG:3022
    EPSG:3022 -> Offsetter
    <UNFILTERED> -> Reprojector
Offsetter
    MODE = Cartesian Coordinate
    XOFF = 1400000
    YOFF = 0
    ZOFF = 0
    OFFSET -> Reprojector
Reprojector
    DEST = EPSG:3006
    INTERPOLATION_TYPE_NAME = Nearest Neighbor
    RASTER_CELL_SIZE = Preserve Cells
    RASTER_TOLERANCE = 0.0
    SOURCE = $(SOURCE)
    REPROJECTED -> AttributeManager
AttributeManager
    ATTR_TABLE:
      SET_TO z = @ZValue()
      SET_TO
    -> GeoObject (writer POSTGIS_2)
GeoObject (writer POSTGIS_2) [off]
    attributes: ObjectId int4, MetaId int4, SymbolId int4
SQLCreator [off]
    DATASET = $(Source_Dest_Dataset_POSTGIS_2)
    EXPOSED_ATTRIBUTE_LIST = ObjectId,MetaId,SymbolId
    FORMAT = POSTGIS
    OUTPUT_FEATURES_DISPLAY = Schema and Data Features
    POSTGIS_CREATE_FEATURE_TABLES_FROM_DATA = Yes
    POSTGIS_DISABLE_COLLECTION_SPLITTING = yes
    POSTGIS_HOST = localhost
    POSTGIS_PORT = 5432
    POSTGIS_QUERY_FEATURE_TYPES_FOR_MERGE_FILTERS = Yes
    POSTGIS_READ_TIME_WITH_TIMEZONE = Yes
    POSTGIS_SSLMODE = prefer
    POSTGIS_USER_NAME = postgres
    POSTGIS_USE_TRUE_POSTGIS_TYPES = yes
    SQL_STATEMENT:
      FME_SQL_DELIMITER ;
      SELECT "ObjectId", "MetaId", "SymbolId", the_raster, ST_Force3D(the_geom) as the_geom
      from public."GeoObject";
