FME workspace path_path2filecopy.fmw

Parameters:
- SourceDataset_PATH = C:\ny_slask\upmus_gpkg   # INCLUDE_WEB_BROWSER Source Folder and File Pathnames Folder
- SourceDataset_PATH_3 = Z:\3 - AGES\UpplandsMuseet\Leverans1\2 - Bearbetning\reprojected   # INCLUDE_WEB_BROWSER Source Folder and File Pathnames Folder
- DestDataset_FILECOPY = C:\ny_slask\upmus_gpkg   # Destination File Copy Folder

Readers:
- PATH_1: PATH from $(SourceDataset_PATH)
- PATH_2: PATH from $(SourceDataset_PATH_3)

Writers:
- FILECOPY_1: FILECOPY to $(DestDataset_FILECOPY)

PATH (reader PATH_1)
    attributes: path_unix buffer, path_windows buffer, path_rootname buffer, path_filename buffer, path_extension buffer, path_directory_unix buffer, path_directory_windows buffer, path_type char(10)
    -> FeatureMerger [REQUESTOR]
PATH (reader PATH_2)
    attributes: path_unix buffer, path_windows buffer, path_rootname buffer, path_filename buffer, path_extension buffer, path_directory_unix buffer, path_directory_windows buffer, path_type char(10)
    -> FeatureMerger [SUPPLIER]
FeatureMerger
    ATTR_ACCUM_MODE = Merge Supplier
    ATTR_CONFLICT_RES_LOOKUP = REQUESTOR_IF_CONFLICT
    IGNORE_NULLS = No
    JOIN_KEYS = @Value(path_rootname) @Value(path_rootname) AUTO
    MERGE_TYPE = Attributes Only
    PROCESS_DUPS = NO
    REJECT_NULL_MISSING_KEYS = No
    SUPPLIERS_FIRST = No
    ATTR_CONFLICT_RES = Use Requestor
    UNMERGED_REQUESTOR -> AttributeManager
AttributeManager
    ATTR_TABLE = RENAME_SET_VALUE path_windows > filecopy_source_dataset (buffer)
    -> diff (writer FILECOPY_1)
diff (writer FILECOPY_1)
