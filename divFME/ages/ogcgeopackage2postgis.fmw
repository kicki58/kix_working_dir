FME workspace ogcgeopackage2postgis.fmw

Parameters:
- SourceDataset_OGCGEOPACKAGE = C:\ny_slask\Leverans_Jamtli\Leverans\aggragated.gpkg   # GeoPackage File
- DestDataset_POSTGIS = uuc-srv390_ages_5434   # Connection
- SourceDataset_POSTGIS = uuc-srv390_ages_5434   # Connection
- SourceDataset_POSTGISinternalAges = uuc-srv390_ages_5434   # Connection internal-ages

Readers:
- OGCGEOPACKAGE_1: OGCGEOPACKAGE from $(SourceDataset_OGCGEOPACKAGE) in EPSG:3006
- POSTGIS_2: POSTGIS from $(SourceDataset_POSTGIS) in EPSG:3006
- POSTGIS_3: POSTGIS from $(SourceDataset_POSTGISinternalAges) in EPSG:3006

Writers:
- POSTGIS_1: POSTGIS to $(DestDataset_POSTGIS) in EPSG:3006

geodata_info (reader POSTGIS_2)
    attributes: geopackage text, gpkg_uuid uuid,PrimaryKey, leverans text
    -> GeometryRemover
GeometryRemover
    REMOVE_COORDSYS = No
    -> FeatureMerger [REQUESTOR]
features (reader OGCGEOPACKAGE_1)
    attributes: gpkg-name text, id int,PrimaryKey
    -> Aggregator
Aggregator
    ACCUM_ATTRS = None
    AGGREGATE_TYPE = Homogeneous Collection (If Possible)
    GROUP_BY = gpkg-name
    MODE = Geometry - Assemble One Level
    SEP = ,
    AGGREGATE -> CenterPointExtractor
CenterPointExtractor
    CENTX = _inside_x
    CENTY = _inside_y
    CENTZ = _inside_z
    EXTRACTIONMODE = CENTER
    -> VertexCreator
VertexCreator
    COORDSYS = EPSG:3006
    MEASURE_TYPE_LOOKUP = CONTINUOUS
    MODE = REPLACE
    REMOVE_ATTRIBUTES = No
    XVAL = @Value(_inside_x)
    YVAL = @Value(_inside_y)
    MEASURE_TYPE = Continuous
    MODE_NAME = Replace with Point
    -> AttributeManager
AttributeManager
    ATTR_TABLE = RENAME_SET_VALUE gpkg-name > geopackage (buffer) = @LowerCase(@Value(geopackage))
    -> geodata_info (writer POSTGIS_1)
    -> FeatureMerger [SUPPLIER]
FeatureMerger
    ATTR_ACCUM_MODE = Merge Supplier
    ATTR_CONFLICT_RES_LOOKUP = REQUESTOR_IF_CONFLICT
    IGNORE_NULLS = No
    JOIN_KEYS = @Value(geopackage) @Value(geopackage) AUTO
    MERGE_TYPE_VAL = GEOM_AND_ATTRS
    PRESERVE_FEATURE_ORDER_LOOKUP = PER_OUTPUT_PORT
    PROCESS_DUPS = NO
    REJECT_NULL_MISSING_KEYS = No
    SUPPLIERS_FIRST = No
    ATTR_CONFLICT_RES = Use Requestor
    MERGE_TYPE = Attributes and Geometry
    MERGED -> SpatialFilter [Candidate]
sverige_buff5000 (reader POSTGIS_3)
    attributes: landskap varchar(254), kommentar varchar(150), skala varchar(100), _area_utan_buffer float8
    -> SpatialFilter [Filter]
Note: failed= utanför Sverige
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS CONTAINS TOUCHES
    USE_BOUNDING_BOX = No
    PASSED -> AttributeManager_2
AttributeManager_2
    ATTR_TABLE:
      REMOVE landskap
      REMOVE kommentar
      REMOVE skala
      REMOVE _area_utan_buffer
      REMOVE _predicate
      REMOVE _inside_x
      REMOVE _inside_y
      REMOVE _inside_z
    -> geodata_info (writer POSTGIS_1)
geodata_info (writer POSTGIS_1)
    attributes: geopackage text, gpkg_uuid uuid,PrimaryKey, leverans text
