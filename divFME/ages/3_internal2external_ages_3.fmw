FME workspace 3_internal2external_ages_3.fmw

Parameters:
- SourceDataset_POSTGISinternalAges = uuc-srv390_ages_5434   # Connection internal-ages
- url2uo = https://pub.raa.se/visa/aktivitet/arkeologisktuppdrag   # url till arkeologiskt uppdrag
- SourceDataset_OGCGEOPACKAGE_3 = C:\ny_slask\SAU_lev2\indata\arkeologiska_uppdrag_undersökningsområden_sverige.gpkg   # arkeologiska_uppdrag_undersökningsområden_sverige.gpkg
- link_geodata = https://swedigarch-ages.arkeologi.uu.se/gpkg/   # link2geodata
- leverans = KMHalland_lev5   # Leverans
- link2rapport_info = https://pub.raa.se/visa/dokumentation/   # Link to rapport info
- DestDataset_POSTGIS = ages-external   # Connection

Readers:
- POSTGIS_3: POSTGIS from $(SourceDataset_POSTGISinternalAges) in EPSG:3006
- OGCGEOPACKAGE_1: OGCGEOPACKAGE from $(SourceDataset_OGCGEOPACKAGE_3)
- POSTGRES_1: POSTGRES from $(SourceDataset_POSTGISinternalAges)

Writers:
- POSTGIS_1: POSTGIS to $(DestDataset_POSTGIS) in EPSG:3006

geodata_info (reader POSTGIS_3)
    attributes: geopackage text, gpkg_uuid uuid,PrimaryKey, leverans text
    -> Tester_3
Tester_3
    BOOL_OP = OR
    TEST_CLAUSE = TEST @Value(leverans) = $(leverans)
    TEST_MODE = TEST
    PASSED -> SpatialFilter [Candidate]
sverige_buff5000 (reader POSTGIS_3)
    attributes: landskap varchar(254), kommentar varchar(150), skala varchar(100), _area_utan_buffer float8
    -> SpatialFilter [Filter]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS CONTAINS TOUCHES
    USE_BOUNDING_BOX = No
    PASSED -> AttributeKeeper
AttributeKeeper
    CREATE_BULK_MODE_FEATURES = NO
    KEEP_ATTRS = geopackage,gpkg_uuid
    -> FeatureMerger [SUPPLIER]
rapport_uppdrag (reader POSTGRES_1)
    attributes: uuid_uppdrag varchar(36), uuid_rapport varchar(36), rapport varchar(78), rapport_info varchar(69)
    -> FeatureMerger_4 [SUPPLIER]
rel2uppdrag (reader POSTGRES_1)
    attributes: gpkg_uuid uuid, uppdrag_uuid uuid
    -> AttributeManager_4
    -> FeatureMerger_2 [REQUESTOR]
AttributeManager_4
    ATTR_TABLE = SET_TO link_fornsok (varchar(200)) = $(url2uo)/@Value(uppdrag_uuid)
    -> FeatureMerger_4 [REQUESTOR]
FeatureMerger_4
    ATTR_ACCUM_MODE = Merge Supplier
    ATTR_CONFLICT_RES_LOOKUP = REQUESTOR_IF_CONFLICT
    CLEANING_TOLERANCE_LOOKUP = AUTO
    CONNECT_Z_MODE_LOOKUP = FIRST_WINS
    GEOM_TYPE_VAL = POLYGONS
    IGNORE_NULLS = No
    JOIN_KEYS = @Value(uppdrag_uuid) @Value(uuid_uppdrag) AUTO
    LIST_ATTRS_TO_INCLUDE = rapport rapport_info uuid_rapport uuid_uppdrag
    LIST_NAME = lit
    MERGE_TYPE = Attributes Only
    PROCESS_DUPS = YES
    REJECT_NULL_MISSING_KEYS = No
    SUPPLIERS_FIRST = No
    ATTR_CONFLICT_RES = Use Requestor
    CLEANING_TOLERANCE = Automatic
    CONNECT_Z_MODE = First Wins
    GEOM_TYPE = Build Polygons
    MERGED -> fix_rapporter_2
    UNMERGED_REQUESTOR -> AttributeManager_2
fix_rapporter_2
    GPKG_UUID = @Value(gpkg_uuid)
    RAPPORT = @Value(rapport)
    RAPPORT_INFO = @Value(rapport_info)
    UO_ID = @Value(uppdrag_uuid)
    UPPDRAG = https://app.raa.se/open/fornsok/uppdrag/@Value(uppdrag_uuid)
    UUID_RAPPORT = @Value(uuid_rapport)
    UUID_UPPDRAG = @Value(uuid_uppdrag)
    link2rapport_info = $(link2rapport_info)
    -> StringReplacer
StringReplacer
    CASE = NO
    FIND_TEXT = "
    NO_MATCH = _FME_NO_OP_
    REGEXP = NO
    SRC_ATTRS = _concatenated_forfattare,_concatenated_rapport,_concatenated_titel,_concatenated_utgivningsar
    -> FeatureMerger_5 [SUPPLIER]
Note: Ingen rapport- kollar vår tabell / fixar till uuid namn så fm funkar
AttributeManager_2
    ATTR_TABLE = RENAME_SET_VALUE uppdrag_uuid > uuid_uppdrag (buffer)
    -> FeatureMerger_5 [SUPPLIER]
FeatureMerger_2
    ATTR_ACCUM_MODE = Merge Supplier
    ATTR_CONFLICT_RES_LOOKUP = REQUESTOR_IF_CONFLICT
    IGNORE_NULLS = No
    JOIN_KEYS = @Value(uppdrag_uuid) @Value(id) AUTO
    MERGE_TYPE = Attributes Only
    PRESERVE_FEATURE_ORDER_LOOKUP = PER_OUTPUT_PORT
    PROCESS_DUPS = NO
    REJECT_NULL_MISSING_KEYS = No
    SUPPLIERS_FIRST = No
    ATTR_CONFLICT_RES = Use Requestor
    MERGED -> FeatureMerger [REQUESTOR]
Note: 1 gpkg -> m uo / Hanteras ,med concatenerad list / m gpkg ->1 uo / behöver inte hanteras då´det skapas en rad för varje gpkg / 1 gpkg-> 0 uo / behöver hanteras separat
FeatureMerger
    ATTR_ACCUM_MODE = Merge Supplier
    ATTR_CONFLICT_RES_LOOKUP = REQUESTOR_IF_CONFLICT
    IGNORE_NULLS = No
    JOIN_KEYS = @Value(gpkg_uuid) @Value(gpkg_uuid) AUTO
    MERGE_TYPE = Attributes and Geometry
    PRESERVE_FEATURE_ORDER_LOOKUP = PER_OUTPUT_PORT
    PROCESS_DUPS = NO
    REJECT_NULL_MISSING_KEYS = No
    SUPPLIERS_FIRST = No
    ATTR_CONFLICT_RES = Use Requestor
    MERGED -> DuplicateFilter_2
    MERGED -> FeatureMerger_5 [REQUESTOR]
FeatureMerger_5
    ATTR_ACCUM_MODE = Merge Supplier
    ATTR_CONFLICT_RES_LOOKUP = REQUESTOR_IF_CONFLICT
    CLEANING_TOLERANCE_LOOKUP = AUTO
    CONNECT_Z_MODE_LOOKUP = FIRST_WINS
    GEOM_TYPE_VAL = POLYGONS
    IGNORE_NULLS = No
    JOIN_KEYS = @Value(uppdrag_uuid) @Value(uuid_uppdrag) AUTO
    MERGE_TYPE = Attributes Only
    PROCESS_DUPS = YES
    REJECT_NULL_MISSING_KEYS = No
    SUPPLIERS_FIRST = No
    ATTR_CONFLICT_RES = Use Requestor
    CLEANING_TOLERANCE = Automatic
    CONNECT_Z_MODE = First Wins
    GEOM_TYPE = Build Polygons
    MERGED -> ListBuilder
AttributeRemover
    LIST_ATTRS = _list{} _list{}._concatenatedLinkRapportInfo _list{}._concatenated_forfattare _list{}._concatenated_rapport _list{}._concatenated_rapport_info _list{}._concatenated_titel _list{}._concatenated_utgivningsar _list{}.beslutande_myndighet _list{}.beslutsdatum _list{}.diarienummer _list{}.kommun _list{}.lan _list{}.socken _list{}.uppdragsnummer _list{}.uppdragstyp _list{}.url _list{}.utforande_organisation
    -> FeatureMerger_3 [REQUESTOR]
ListExploder
    ATTR_ACCUM_MODE = Merge List Attributes
    ATTR_CONFLICT_RES_LOOKUP = INCOMING_IF_CONFLICT
    INDEX_ATTR = _element_index
    LIST_ATTR = _list{}
    ATTR_CONFLICT_RES = Use List Attribute Values
    ELEMENTS -> AttributeManager_3
AttributeManager_3
    ATTR_TABLE:
      RENAME_SET_VALUE _concatenated_forfattare > forfattare (buffer)
      RENAME_SET_VALUE _concatenated_titel > titel (buffer)
      RENAME_SET_VALUE _concatenated_utgivningsar > utgivningsar (buffer)
      RENAME_SET_VALUE _concatenated_rapport > rapport (buffer)
      RENAME_SET_VALUE _concatenatedLinkRapportInfo > link_rapport_info (buffer)
      REMOVE _element_index (uint32)
      REMOVE _concatenated_rapport_info (buffer)
    -> FeatureMerger_3 [REQUESTOR]
DuplicateFilter_2
    INPUT_ORDERED_CHOICE_LOOKUP = NO
    KEYATTR = gpkg_uuid
    PRESERVE_FEATURE_ORDER_LOOKUP = PER_OUTPUT_PORT
    INPUT_ORDERED_CHOICE = No
    UNIQUE -> FeatureMerger_3 [SUPPLIER]
Note: lägg tillbaka geometrierna
FeatureMerger_3
    JOIN_KEYS = @Value(gpkg_uuid) @Value(gpkg_uuid) AUTO
    MERGE_TYPE = Geometry
    PRESERVE_FEATURE_ORDER_LOOKUP = PER_OUTPUT_PORT
    PROCESS_DUPS = NO
    REJECT_NULL_MISSING_KEYS = No
    SUPPLIERS_FIRST = No
    MERGED -> AttributeManager
AttributeManager
    ATTR_TABLE:
      RENAME_SET_VALUE geopackage > geodatafil
      SET_TO link_geodata = $(link_geodata)@Value(geodatafil).gpkg
      RENAME_SET_VALUE url > link_fornsok
      REMOVE rapport
      REMOVE _element_count
      REMOVE rapport_info
      REMOVE uppdrag_uuid
      REMOVE id
      REMOVE gpkg_uuid
    -> geodata_info (writer POSTGIS_1)
rapportLank (reader POSTGRES_1) [off]
    attributes: gpkg_uuid uuid, rapportejkmr text
FeatureMerger_6 [off]
    ATTR_ACCUM_MODE = Merge Supplier
    ATTR_CONFLICT_RES_LOOKUP = REQUESTOR_IF_CONFLICT
    IGNORE_NULLS = No
    MERGE_TYPE = Attributes Only
    PROCESS_DUPS = No
    REJECT_NULL_MISSING_KEYS = No
    SUPPLIERS_FIRST = No
    ATTR_CONFLICT_RES = Use Requestor

Bookmark: uo
arkeologiska_uppdrag_undersökningsområden_sverige_linestring (reader OGCGEOPACKAGE_1)
    attributes: id text(255), uppdragsnummer text(9), beslutande_myndighet text(255), beslutsdatum date, diarienummer text(255), uppdragstyp text(255), utforande_organisation text(255), nollresultat text(9), url text(255), status text(255), lan text, kommun text, socken text, fid int,PrimaryKey
    -> Tester
arkeologiska_uppdrag_undersökningsområden_sverige_point (reader OGCGEOPACKAGE_1)
    attributes: id text(255), uppdragsnummer text(9), beslutande_myndighet text(255), beslutsdatum date, diarienummer text(255), uppdragstyp text(255), utforande_organisation text(255), nollresultat text(9), url text(255), status text(255), lan text, kommun text, socken text, fid int,PrimaryKey
    -> Tester
arkeologiska_uppdrag_undersökningsområden_sverige_polygon (reader OGCGEOPACKAGE_1)
    attributes: id text(255), uppdragsnummer text(9), beslutande_myndighet text(255), beslutsdatum date, diarienummer text(255), uppdragstyp text(255), utforande_organisation text(255), nollresultat text(9), url text(255), status text(255), lan text, kommun text, socken text, fid int,PrimaryKey
    -> Tester
Tester
    BOOL_OP = OR
    TEST_CLAUSE = TEST 0 = 0
    TEST_MODE = TEST
    PASSED -> AttributeKeeper_2
AttributeKeeper_2
    CREATE_BULK_MODE_FEATURES = NO
    KEEP_ATTRS = id,uppdragsnummer,beslutande_myndighet,beslutsdatum,diarienummer,kommun,lan,socken,uppdragstyp,url,utforande_organisation
    -> DuplicateFilter
DuplicateFilter
    INPUT_ORDERED_CHOICE_LOOKUP = NO
    KEYATTR = id uppdragsnummer
    PRESERVE_FEATURE_ORDER_LOOKUP = PER_OUTPUT_PORT
    INPUT_ORDERED_CHOICE = No
    UNIQUE -> FeatureMerger_2 [SUPPLIER]

Bookmark: list
ListBuilder
    GROUP_BY = geopackage gpkg_uuid
    LIST_ATTRS_TO_INCLUDE = beslutande_myndighet beslutsdatum diarienummer id kommun lan socken uppdragsnummer uppdragstyp url utforande_organisation gpkg_uuid _concatenated_forfattare _concatenated_rapport _concatenated_rapport_info _concatenated_titel geopackage uppdrag_uuid _concatenatedLinkRapportInfo _concatenated_utgivningsar
    LIST_NAME = _list
    -> ListElementCounter
ListElementCounter
    CNT_ATTR = _element_count
    LIST_NAME = _list{}
    -> Tester_2
Note: har listan mer än ett element?
Tester_2
    BOOL_OP = OR
    TEST_CLAUSE = TEST @Value(_element_count) > 1
    TEST_MODE = TEST
    PASSED -> concatAttributes [ListExploder_Input]
    FAILED -> ListExploder
concatAttributes
    GEOPACKAGE = @Value(geopackage)
    GPKG_UUID = @Value(gpkg_uuid)
    LIST_ATTR = _list{}
    -> AttributeRemover

Bookmark: KOLLA TABLE HANDLING
geodata_info (writer POSTGIS_1)
    attributes: geodatafil text, uppdragsnummer text, uppdragstyp text, diarienummer text, utforande_organisation text, beslutande_myndighet text, beslutsdatum text, kommun text, lan text, socken text, link_geodata text, link_fornsok text, forfattare varchar, titel varchar, utgivningsar varchar, link_rapport_info varchar

FME custom transformer fix_rapporter

Parameters:
- RAPPORT = @Value(rapport)   # rapport
- RAPPORT_INFO = @Value(rapport_info)   # Rapport Info
- UO_ID = @Value(uo_id)   # Uo Id
- UPPDRAG = @Value(uppdrag)   # uppdrag
- UUID_RAPPORT = @Value(uuid_rapport)   # Uuid Rapport
- UUID_UPPDRAG = @Value(uuid_uppdrag)   # Uuid Uppdrag
- GPKG_UUID = @Value(gpkg_uuid)   # Gpkg Uuid
- link2rapport_info = https://app.raa.se/open/arkivsok/document?uri=https:%2F%2Fpub.raa.se%2Fdokumentation%2F   # Link to rapport info

Input (input)
    -> HTTPCaller_2
HTTPCaller_2
    CLIENT_CERTIFICATE_TYPE = NONE
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = @Value(rapport_info)
    TEST_DIALOG_PARAMETERS_FOR_RESPONSE = authConnection; authEnabled;false authMethod;BASIC authPassword; authUsername; contentType; method;GET multipartContentType;FORM_DATA requestUrl;https://pub.raa.se/dokumentation/01be3682-c258-4499-830d-670bdcad38bb uploadData; version;HTTP_2
    TEST_DIALOG_RESPONSE_PREVIEW = {     "attributes": [         {             "label": "Författare",             "name": "forfattare",             "value": [                 "Sundström, Lars",                 "Guinard, Michel",                 "Svenman, Emelie",                 "Andersson, Fredrik"             ]         },         {             "label": "Diarienummer (LST)",             "name": "lansstyrelse_diarienummer",             "value": [                 "15640-2014"             ]         },         {             "label": "Arkiv ID",             "name": "lta_archive_id",             "value": [                 "59515d53-17ab-4a25-8373-a3fd1c75a693"             ]         },         {             "label": "Beslutande myndighet",             "name": "beslutande_myndighet_v2",             "value": [                 "LÄNSSTYRELSEN I STOCKHOLMS LÄN"             ]         },         {             "label": "Ändrad",             "name": "modified_date",             "value": [                 "2023-03-15 14:50:17"             ]         },         {             "label": "Rapportnummer",             "name": "rapportnummer",             "value": [                 "2020:29"             ]         },         {             "label": "Kommun",             "name": "kommun",             "value": [                 "Botkyrka"             ]         },         {             "label": "Handlingstyp",             "name": "genre_form_strikt",             "value": [                 "Rapport"             ]         },         {             "label": "Socken",             "name": "socken",             "value": [                 "Botkyrka"             ]         },         {             "label": "Uppdragstyp",             "name": "uppdragtyp",             "value": [                 "Arkeologisk undersökning"             ]         },         {             "label": "Lämningstyp",             "name": "lamningtyp",             "value": [                 "Boplats"             ]         },         {             "label": "Arkiv/Samling",             "name": "arkiv_samling",             "value": [                 "Uppdragsarkeologiska rapporter 2013-"             ]         },         {             "label": "E-plikt",             "name": "eplikt",             "value": [                 "true"             ]         },         {             "label": "System",             "name": "lta_system",             "value": [                 "Uppdragsregistret"             ]         },         {             "label": "Klassificering",             "name": "klassificering",             "value": [                 "3.5.5"             ]         },         {             "label": "Licens",             "name": "licens",             "value": [                 "https://creativecommons.org/licenses/by/4.0/"             ]         },         {             "label": "Språk",             "name": "sprak",             "value": [                 "Svenska"             ]         },         {             "label": "Tidsperiod",             "name": "tidperiod",             "value": [                 "Järnålder",                 "Bronsålder",                 "Stenålder"             ]         },         {             "label": "Producent",             "name": "lta_producer",             "value": [                 "Arkeologisk utförare"             ]         },         {             "label": "Skapad",             "name": "created_date",             "value": [                 "2021-03-12 09:58:33"             ]         },         {             "label": "Kontext URI",             "name": "kontext_uri",             "value": [                 "https://pub.raa.se/aktivitet/arkeologisktuppdrag/3a9938da-edfb-416f-95a6-27368a2f48ac"             ]         },         {             "label": "Utgivare",             "name": "utgivare",             "value": [                 "STIFTELSEN SOCIETAS ARCHAEOLOGICA UPSALIENSIS"             ]         },         {             "label": "Ändrad av",             "name": "modified_by",             "value": [                 "iipaxSystem"             ]         },         {             "label": "Utförande organisation",             "name": "utforare",             "value": [                 "STIFTELSEN SOCIETAS ARCHAEOLOGICA UPSALIENSIS"             ]         },         {             "label": "Titel",             "name": "titel",             "value": [                 "RIKSTENBOPLATSERNA Arkeologisk undersökning av mesolitiska platser på Södertörn med yxproduktion och stora kokgropar samt utmarksbruk från senneolitikum till äldre järnålder L2017:2912, L2017:2913, L2017:3521, L2017:3368, Riksten 8:1, Botkyrka socken och kommun, Södermanland, Stockholms län"             ]         },         {             "label": "Län",             "name": "lan",             "value": [                 "Stockholm"             ]         },         {             "label": "Informationstyp",             "name": "informationstyp",             "value": [                 "Dokument"             ]         },         {             "label": "Ämnesord",             "name": "amnesord",             "value": [                 "Arkeologi"             ]         },         {             "label": "Landskap",             "name": "landskap",             "value": [                 "Södermanland"             ]         },         {             "label": "Skäl sekretess / paragraf",             "name": "paragraph",             "value": [                 "Utföraren har intygat att dokumentet endast innehåller fotografier för vilka det finns spridningstillstånd eller som inte kräver spridningstillstånd enligt lag (2016:319) om skydd för geografisk miljöinformation."             ]         },         {             "label": "Serienamn",             "name": "serie",             "value": [                 "SAU Rapport"             ]         },         {             "label": "Dokumenttyp",             "name": "dokumenttyp",             "value": [                 "Rapport"             ]         },         {             "label": "Referens/ID",             "name": "display_name",             "value": [                 "201800238 Rapport 01be3682-c258-4499-830d-670bdcad38bb"             ]         },         {             "label": "Arkiveringsdatum",             "name": "lta_archive_date",             "value": [                 "2021-03-12 09:58:21"             ]         },         {             "label": "Uppdragsnummer",             "name": "uppdragnummer",             "value": [                 "201800238"             ]         },         {             "label": "URI",             "name": "uri",             "value": [                 "https://pub.raa.se/dokumentation/01be3682-c258-4499-830d-670bdcad38bb"             ]         },         {             "label": "RAÄ-nummer",             "name": "raanummer",             "value": [                 "L2017:2912",                 "L2017:2913",                 "L2017:3521",                 "L2017:3368"             ]         },         {             "label": "Utgivningsår",             "name": "utgivningsar",             "value": [                 "2020"             ]         }     ],     "documents": [     ],     "license": {         "license": "https://creativecommons.org/licenses/by/4.0/",         "licenseIconUrl": "https://licensebuttons.net/l/by/4.0/80x15.png",         "licenseInformation": null,         "licenseName": "CC-BY 4.0"     },     "presentationLink": "https://pub.raa.se/visa/dokumentation/01be3682-c258-4499-830d-670bdcad38bb",     "resourceGroups": [         {             "presentationThumbnailUrl": "https://pub.raa.se/dokumentation/01be3682-c258-4499-830d-670bdcad38bb/arkivbestandig/miniatyr",             "resources": [                 {                     "created": "2021-03-12 09:58:34",                     "fileExtension": "pdf",                     "fileName": "Rikstenboplatserna.pdf",                     "fileSize": 114579287,                     "format": "arkivbestandig",                     "media": "application/pdf",                     "uri": "https://pub.raa.se/dokumentation/01be3682-c258-4499-830d-670bdcad38bb/arkivbestandig"                 },                 {                     "created": "2021-03-12 09:58:34",                     "fileExtension": "png",                     "fileName": "thumbnail.png",                     "fileSize": 30090,                     "format": "arkivbestandig",                     "media": "image/png",                     "uri": "https://pub.raa.se/dokumentation/01be3682-c258-4499-830d-670bdcad38bb/arkivbestandig/miniatyr"                 },                 {                     "created": "2021-03-12 09:58:34",                     "fileExtension": "pdf",                     "fileName": "Rikstenboplatserna_org.pdf",                     "fileSize": 115433220,                     "format": "original",                     "media": "application/pdf",                     "uri": "https://pub.raa.se/dokumentation/01be3682-c258-4499-830d-670bdcad38bb/original"                 },                 {                     "created": "2021-03-12 09:58:34",                     "fileExtension": "png",                     "fileName": "thumbnail.png",                     "fileSize": 30090,                     "format": "original",                     "media": "image/png",                     "uri": "https://pub.raa.se/dokumentation/01be3682-c258-4499-830d-670bdcad38bb/original/miniatyr"                 }             ],             "securityLevel": "PUBLIC",             "title": "Rikstenboplatserna"         }     ],     "securityLevel": "PUBLIC",     "uri": "https://pub.raa.se/dokumentation/01be3682-c258-4499-830d-670bdcad38bb" }
    TEST_DIALOG_RESPONSE_STATUS = HTTP/1.1 200
    TRANSFER_TIMEOUT_LENGTH = 90
    USE_COOKIES = No
    VERIFY_SSL_CERTIFICATES = Yes
    -> JSONFragmenter_2
JSONFragmenter_2
    EXPLODE_FORMAT = JSON
    EXTRACT_ATTR = Yes
    JSON_ATTR = _response_body
    JSON_QUERY = json["attributes"][*]
    READ_FROM_FILE = NO
    RECURSIVE = YES
    REJECT_EMPTY_LISTS = YES
    FRAGMENTS -> JSONExtractor_2
JSONExtractor_2
    EXTRACT_QUERY_TABLE = name json["name"] value json["value"]
    JSON_DOCUMENT = @Value(_response_body)
    READ_FROM_FILE = NO
    EVALUATED -> AttributeManager_3
AttributeManager_3
    ATTR_TABLE:
      RENAME_SET_VALUE name (varchar(200))
      RENAME_SET_VALUE value (varchar(200)) = @TrimRight(@TrimLeft(@Value(value),'['), ']')
    -> AttributeFilter_2
AttributeFilter_2
    ATTR_NAME = name
    ATTR_VALUES = titel,forfattare,amnesord,arkiv_samling,beslutande_myndighet_v2,created_date,display_name,dokumenttyp,eplikt,genre_form_strikt,informationstyp,klassificering,kommun,kontext_uri,lamningtyp,lan,landskap,lansstyrelse_diarienummer,licens,lta_archive_date,lta_archive_id,lta_producer,lta_system,modified_by,modified_date,paragraph,raanummer,rapportnummer,serie,socken,sprak,tidperiod,uppdragnummer,uppdragtyp,uri,utforare,utgivare,utgivningsar,<Empty>,<Missing>,<Null>,<Unfiltered>
    titel -> AttributeManager_4
    forfattare -> AttributeManager_5
    utgivningsar -> AttributeManager_2
AttributeManager_4
    ATTR_TABLE:
      RENAME_SET_VALUE name > titel_name (varchar(200))
      RENAME_SET_VALUE value > title_value (varchar(200))
      SET_TO link_rapport_info (varchar(200)) = $(link2rapport_info)@Value(uuid_rapport)
    -> ListBuilder
ListBuilder
    GROUP_BY = gpkg_uuid uuid_uppdrag
    LIST_ATTRS_TO_INCLUDE = title_value rapport rapport_info uuid_rapport link_rapport_info
    LIST_NAME = _list_title
    -> ListConcatenator
ListConcatenator
    DROP_EMPTY_PARTS = No
    LIST_ATTR = _list_title{}.title_value
    SEP = " ; "
    VAL_ATTR = _concatenated_titel
    -> ListConcatenator_3
ListConcatenator_3
    DROP_EMPTY_PARTS = No
    LIST_ATTR = _list_title{}.rapport_info
    SEP = " ; "
    VAL_ATTR = _concatenated_rapport_info
    -> ListConcatenator_4
ListConcatenator_4
    DROP_EMPTY_PARTS = No
    LIST_ATTR = _list_title{}.rapport
    SEP = " ; "
    VAL_ATTR = _concatenated_rapport
    -> ListConcatenator_6
ListConcatenator_6
    DROP_EMPTY_PARTS = No
    LIST_ATTR = _list_title{}.link_rapport_info
    SEP = " ; "
    VAL_ATTR = _concatenatedLinkRapportInfo
    -> Aggregator_2
AttributeManager_5
    ATTR_TABLE:
      RENAME_SET_VALUE name > forfattare_name (varchar(200))
      RENAME_SET_VALUE value > forfattare_value (varchar(200))
    -> ListBuilder_2
ListBuilder_2
    GROUP_BY = uuid_uppdrag gpkg_uuid
    LIST_ATTRS_TO_INCLUDE = forfattare_value
    LIST_NAME = _list_forfattare
    -> ListConcatenator_2
ListConcatenator_2
    DROP_EMPTY_PARTS = No
    LIST_ATTR = _list_forfattare{}.forfattare_value
    SEP = " ; "
    VAL_ATTR = _concatenated_forfattare
    -> Aggregator_2
AttributeManager_2
    ATTR_TABLE:
      RENAME_SET_VALUE name > utgivningsar_name (varchar(200))
      RENAME_SET_VALUE value > utgivningsar_value (varchar(200))
    -> ListBuilder_3
ListBuilder_3
    GROUP_BY = uuid_uppdrag gpkg_uuid
    LIST_ATTRS_TO_INCLUDE = utgivningsar_value
    LIST_NAME = _list_utgivningsar
    -> ListConcatenator_5
ListConcatenator_5
    DROP_EMPTY_PARTS = No
    LIST_ATTR = _list_utgivningsar{}.utgivningsar_value
    SEP = " ; "
    VAL_ATTR = _concatenated_utgivningsar
    -> Aggregator_2
Aggregator_2
    ACCUM_ATTRS_NAME = Merge Incoming Attributes
    AGGREGATE_TYPE = Homogeneous Collection (If Possible)
    GROUP_BY = uuid_uppdrag gpkg_uuid
    MODE = Geometry - Assemble One Level
    SEP = ,
    AGGREGATE -> Output (output)
Output (output)

FME custom transformer concatAttributes

Parameters:
- LIST_ATTR = _list{}   # "" List Attribute
- GPKG_UUID = @Value(gpkg_uuid)   # Gpkg Uuid
- GEOPACKAGE = @Value(geopackage)   # geopackage

ListExploder_Input (input)
    -> ListExploder
ListExploder
    ATTR_ACCUM_MODE = Merge List Attributes
    ATTR_CONFLICT_RES_LOOKUP = INCOMING_IF_CONFLICT
    INDEX_ATTR = _element_index
    LIST_ATTR = $(LIST_ATTR)
    ATTR_CONFLICT_RES = Use List Attribute Values
    ELEMENTS -> ListBuilder_3
    ELEMENTS -> ListBuilder_2
    ELEMENTS -> ListBuilder_4
    ELEMENTS -> ListBuilder_5
    ELEMENTS -> ListBuilder_6
    ELEMENTS -> ListBuilder_7
    ELEMENTS -> ListBuilder_8
    ELEMENTS -> ListBuilder_9
    ELEMENTS -> ListBuilder_10
    ELEMENTS -> ListBuilder_11
    ELEMENTS -> ListBuilder_12
    ELEMENTS -> ListBuilder_13
    ELEMENTS -> ListBuilder_14
    ELEMENTS -> ListBuilder_15
    ELEMENTS -> ListBuilder_16
    ELEMENTS -> ListBuilder_17
ListBuilder_2
    GROUP_BY = geopackage
    LIST_ATTRS_TO_INCLUDE = uppdragsnummer
    LIST_NAME = _list
    -> ListDuplicateRemover
ListDuplicateRemover
    SRC_LIST = _list{}.uppdragsnummer
    -> ListConcatenator
ListConcatenator
    DROP_EMPTY_PARTS = No
    LIST_ATTR = _list{}.uppdragsnummer
    SEP = " , "
    VAL_ATTR = uppdragsnummer
    -> Aggregator
ListBuilder_3
    GROUP_BY = geopackage
    LIST_ATTRS_TO_INCLUDE = beslutande_myndighet
    LIST_NAME = _list
    -> ListDuplicateRemover_2
ListDuplicateRemover_2
    SRC_LIST = _list{}.beslutande_myndighet
    -> ListConcatenator_2
ListConcatenator_2
    DROP_EMPTY_PARTS = No
    LIST_ATTR = _list{}.beslutande_myndighet
    SEP = " , "
    VAL_ATTR = beslutande_myndighet
    -> Aggregator
ListBuilder_4
    GROUP_BY = geopackage
    LIST_ATTRS_TO_INCLUDE = beslutande_myndighet beslutsdatum
    LIST_NAME = _list
    -> ListDuplicateRemover_3
ListDuplicateRemover_3
    SRC_LIST = _list{}.beslutsdatum
    -> ListConcatenator_3
ListConcatenator_3
    DROP_EMPTY_PARTS = No
    LIST_ATTR = _list{}.beslutsdatum
    SEP = " , "
    VAL_ATTR = beslutsdatum
    -> Aggregator
ListBuilder_5
    GROUP_BY = geopackage
    LIST_ATTRS_TO_INCLUDE = diarienummer
    LIST_NAME = _list
    -> ListDuplicateRemover_4
ListDuplicateRemover_4
    SRC_LIST = _list{}.diarienummer
    -> ListConcatenator_4
ListConcatenator_4
    DROP_EMPTY_PARTS = No
    LIST_ATTR = _list{}.diarienummer
    SEP = " , "
    VAL_ATTR = diarienummer
    -> Aggregator
ListBuilder_6
    GROUP_BY = geopackage
    LIST_ATTRS_TO_INCLUDE = uppdragstyp
    LIST_NAME = _list
    -> ListDuplicateRemover_5
ListDuplicateRemover_5
    SRC_LIST = _list{}.uppdragstyp
    -> ListConcatenator_5
ListConcatenator_5
    DROP_EMPTY_PARTS = No
    LIST_ATTR = _list{}.uppdragstyp
    SEP = " , "
    VAL_ATTR = uppdragstyp
    -> Aggregator
ListBuilder_7
    GROUP_BY = geopackage
    LIST_ATTRS_TO_INCLUDE = utforande_organisation
    LIST_NAME = _list
    -> ListDuplicateRemover_6
ListDuplicateRemover_6
    SRC_LIST = _list{}.utforande_organisation
    -> ListConcatenator_6
ListConcatenator_6
    DROP_EMPTY_PARTS = No
    LIST_ATTR = _list{}.utforande_organisation
    SEP = " , "
    VAL_ATTR = utforande_organisation
    -> Aggregator
ListBuilder_8
    GROUP_BY = geopackage
    LIST_ATTRS_TO_INCLUDE = url
    LIST_NAME = _list
    -> ListDuplicateRemover_7
ListDuplicateRemover_7
    SRC_LIST = _list{}.url
    -> ListConcatenator_7
ListConcatenator_7
    DROP_EMPTY_PARTS = No
    LIST_ATTR = _list{}.url
    SEP = " , "
    VAL_ATTR = url
    -> Aggregator
ListBuilder_9
    GROUP_BY = geopackage
    LIST_ATTRS_TO_INCLUDE = lan
    LIST_NAME = _list
    -> ListDuplicateRemover_8
ListDuplicateRemover_8
    SRC_LIST = _list{}.lan
    -> ListConcatenator_8
ListConcatenator_8
    DROP_EMPTY_PARTS = No
    LIST_ATTR = _list{}.lan
    SEP = " , "
    VAL_ATTR = lan
    -> Aggregator
ListBuilder_10
    GROUP_BY = geopackage
    LIST_ATTRS_TO_INCLUDE = kommun
    LIST_NAME = _list
    -> ListDuplicateRemover_9
ListDuplicateRemover_9
    SRC_LIST = _list{}.kommun
    -> ListConcatenator_9
ListConcatenator_9
    DROP_EMPTY_PARTS = No
    LIST_ATTR = _list{}.kommun
    SEP = " , "
    VAL_ATTR = kommun
    -> Aggregator
ListBuilder_11
    GROUP_BY = geopackage
    LIST_ATTRS_TO_INCLUDE = socken
    LIST_NAME = _list
    -> ListDuplicateRemover_10
ListDuplicateRemover_10
    SRC_LIST = _list{}.socken
    -> ListConcatenator_10
ListConcatenator_10
    DROP_EMPTY_PARTS = No
    LIST_ATTR = _list{}.socken
    SEP = " , "
    VAL_ATTR = socken
    -> Aggregator
Aggregator
    ACCUM_ATTRS_NAME = Merge Incoming Attributes
    AGGREGATE_TYPE = Homogeneous Collection (If Possible)
    GROUP_BY = geopackage
    MODE = Geometry - Assemble One Level
    SEP = ,
    AGGREGATE -> Output (output)
Output (output)

Bookmark: Rapport
ListBuilder_12
    GROUP_BY = geopackage
    LIST_ATTRS_TO_INCLUDE = _concatenated_forfattare
    LIST_NAME = _list
    -> ListConcatenator_11
ListConcatenator_11
    DROP_EMPTY_PARTS = No
    LIST_ATTR = _list{}._concatenated_forfattare
    SEP = " ; "
    VAL_ATTR = forfattare
    -> Aggregator
ListBuilder_13
    GROUP_BY = geopackage
    LIST_ATTRS_TO_INCLUDE = _concatenated_titel
    LIST_NAME = _list
    -> ListConcatenator_12
ListConcatenator_12
    DROP_EMPTY_PARTS = No
    LIST_ATTR = _list{}._concatenated_titel
    SEP = " ; "
    VAL_ATTR = titel
    -> Aggregator
ListBuilder_14
    GROUP_BY = geopackage
    LIST_ATTRS_TO_INCLUDE = _concatenated_rapport_info
    LIST_NAME = _list
    -> ListConcatenator_13
ListConcatenator_13
    DROP_EMPTY_PARTS = No
    LIST_ATTR = _list{}._concatenated_rapport_info
    SEP = " ; "
    VAL_ATTR = rapport_info
    -> Aggregator
ListBuilder_15
    GROUP_BY = geopackage gpkg_uuid
    LIST_ATTRS_TO_INCLUDE = _concatenated_rapport
    LIST_NAME = _list
    -> ListConcatenator_14
ListConcatenator_14
    DROP_EMPTY_PARTS = No
    LIST_ATTR = _list{}._concatenated_rapport
    SEP = " ; "
    VAL_ATTR = rapport
    -> Aggregator
ListBuilder_16
    GROUP_BY = geopackage gpkg_uuid
    LIST_ATTRS_TO_INCLUDE = _concatenated_rapport _concatenatedLinkRapportInfo
    LIST_NAME = _list
    -> ListConcatenator_15
ListConcatenator_15
    DROP_EMPTY_PARTS = No
    LIST_ATTR = _list{}._concatenatedLinkRapportInfo
    SEP = " ; "
    VAL_ATTR = link_rapport_info
    -> Aggregator
ListBuilder_17
    GROUP_BY = geopackage gpkg_uuid
    LIST_ATTRS_TO_INCLUDE = _concatenatedLinkRapportInfo _concatenated_utgivningsar
    LIST_NAME = _list
    -> ListConcatenator_16
ListConcatenator_16
    DROP_EMPTY_PARTS = No
    LIST_ATTR = _list{}._concatenated_utgivningsar
    SEP = " ; "
    VAL_ATTR = utgivningsar
    -> Aggregator
