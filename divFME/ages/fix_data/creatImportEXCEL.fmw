FME workspace creatImportEXCEL.fmw

Parameters:
- SourceDataset_XLSXR = C:\Users\krima354\Box\SweDigArch M3\Temp\yun2\leverans2_Intrasisprojekt som skickas till UU_241021.xlsx   # Source Microsoft Excel File(s)

Readers:
- XLSXR_1: XLSXR from $(SourceDataset_XLSXR)

location_checking (reader XLSXR_1)
    attributes: Filnamn databas char(32), LÄN char(15), Kommentar char(33), Uppdragsnummer char(20), Uppdragnummmer_updated number(9,0), Rapport char(534), Rapport filnamn char(21), Länk till rapport char(149), Location_checking char(98), Sekretess string, K string, L string, M string, N string, O string, P string, Q string, R string, S string, T string, U string
    -> Tester
Tester
    BOOL_OP = OR
    TEST_CLAUSE = TEST Filnamn databas NOT_ATTRIBUTE_HAS_A_VALUE ""
    TEST_MODE = TEST
    FAILED -> AttributeManager
AttributeManager
    ATTR_TABLE:
      SET_TO geopackage (varchar(200)) = @LowerCase(@Value(Filnamn databas))
      REMOVE K (buffer)
      REMOVE L (buffer)
      REMOVE M (buffer)
      REMOVE N (buffer)
      REMOVE O (buffer)
      REMOVE P (buffer)
      REMOVE Q (buffer)
      REMOVE R (buffer)
      REMOVE S (buffer)
      REMOVE T (buffer)
      REMOVE U (buffer)
    -> AttributeFilter
AttributeFilter
    ATTR_NAME = Location_checking
    ATTR_VALUES = <Empty>,<Missing>,<Null>,<Unfiltered>,no geopackage
    <UNFILTERED> -> AttributeFilter_3
AttributeFilter_3
    ATTR_NAME = Uppdragsnummer
    ATTR_VALUES = <Empty>,<Missing>,<Null>,<Unfiltered>,Ej inlagd i KMR
    <UNFILTERED> -> AttributeFilter_2
Note: kör bara in de som är oki
AttributeFilter_2
    ATTR_NAME = Länk till rapport
    ATTR_VALUES = <Empty>,<Missing>,<Null>,<Unfiltered>,Ej uppladad,FME_NULL_VALUE,https://www.kmmd.se/s/KM2018_31_Inlaga.pdf,Länk saknas
