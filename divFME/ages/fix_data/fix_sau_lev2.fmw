FME workspace fix_sau_lev2.fmw

Parameters:
- SourceDataset_PATH = C:\ny_slask\SAU_lev2   # INCLUDE_WEB_BROWSER Source Folder and File Pathnames Folder
- SourceDataset_XLSXR = C:\ny_slask\SAU_lev2\indata\SAU_nyare_undersokningar.xlsx   # Source Microsoft Excel File(s)
- DestDataset_XLSXW = C:\ny_slask\SAU_lev2\indata\SAU_nyare_undersokningar2.xlsx   # Destination Microsoft Excel File

Readers:
- PATH_1: PATH from $(SourceDataset_PATH)
- XLSXR_1: XLSXR from $(SourceDataset_XLSXR)

Writers:
- XLSXW_1: XLSXW to $(DestDataset_XLSXW)

import (reader XLSXR_1)
    attributes: Filnamn databas char(30), Kommentar char(34), Uppdragsnummer number(10,0), Rapport i arkivsök char(4), Länk till rapport(ej arkivsök) char(124), Sekretess char(1)
    -> FeatureMerger_2 [REQUESTOR]
    -> FeatureMerger_3 [SUPPLIER]
PATH (reader PATH_1)
    attributes: path_unix buffer, path_windows buffer, path_rootname buffer, path_filename buffer, path_extension buffer, path_directory_unix buffer, path_directory_windows buffer, path_type char(10)
    -> FeatureMerger_2 [SUPPLIER]
FeatureMerger_2
    ATTR_ACCUM_MODE = Merge Supplier
    ATTR_CONFLICT_RES = Use Requestor
    IGNORE_NULLS = No
    JOIN_KEYS = @Value(Filnamn databas) @Value(path_rootname) AUTO
    MERGE_TYPE = Attributes Only
    PROCESS_DUPS = NO
    REJECT_NULL_MISSING_KEYS = No
    SUPPLIERS_FIRST = No
    MERGED -> import (writer XLSXW_1)
    UNMERGED_REQUESTOR -> FeatureMerger [SUPPLIER]
    UNUSED_SUPPLIER -> AttributeManager_3
AttributeManager_3
    ATTR_TABLE = SET_TO correct_file_name = @Value(path_rootname)
    -> AttributeManager
AttributeManager
    ATTR_TABLE = SET_TO path_rootname = @ReplaceString(@Value(path_rootname),"_","",caseSensitive=TRUE)
    -> FeatureMerger_3 [REQUESTOR]
FeatureMerger_3
    ATTR_ACCUM_MODE = Merge Supplier
    ATTR_CONFLICT_RES = Use Requestor
    IGNORE_NULLS = No
    JOIN_KEYS = @Value(path_rootname) @Value(Filnamn databas) AUTO
    MERGE_TYPE = Attributes Only
    PROCESS_DUPS = NO
    REJECT_NULL_MISSING_KEYS = No
    SUPPLIERS_FIRST = No
    MERGED -> FeatureMerger [REQUESTOR]
FeatureMerger
    ATTR_ACCUM_MODE = Merge Supplier
    ATTR_CONFLICT_RES = Use Requestor
    IGNORE_NULLS = No
    JOIN_KEYS = @Value(Uppdragsnummer) @Value(Uppdragsnummer) AUTO
    MERGE_TYPE = Attributes Only
    PROCESS_DUPS = NO
    REJECT_NULL_MISSING_KEYS = No
    SUPPLIERS_FIRST = No
    MERGED -> AttributeManager_2
    UNUSED_SUPPLIER -> import (writer XLSXW_1)
    <REJECTED> -> import (writer XLSXW_1)
AttributeManager_2
    ATTR_TABLE = SET_TO Filnamn databas = @Value(correct_file_name)
    -> import (writer XLSXW_1)
import (writer XLSXW_1)
    attributes: Filnamn databas string(30), Kommentar string(34), Uppdragsnummer number(10), Rapport i arkivsök string(4), Länk till rapport(ej arkivsök) string(124), Sekretess string(1)
