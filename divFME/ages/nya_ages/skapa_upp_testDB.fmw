FME workspace skapa_upp_testDB.fmw
Title: SAUimportIntrasis
Description: En import av SAU's databaser.
Vad som krävs
C:\Intrasis\backup_files
Backupfiler med vissa namn ändrade (de som har _ innan datumet i slutet)
pgpass.conf - med lösen för den dbhanteraren som man går mot
i katalogen C:\Users\krima354\AppData\Roaming\postgresql

Parameters:
- DestDataset_POSTGRES_3 = ages_test   # Database
- DestDataset_POSTGRES_4 = ages_test   # Database
- server = localhost   # Server
- dbversion = 16
- port = 5434   # Port
- user = postgres   # User
- SourceDataset_TEXTLINE = $(FME_MF_DIR)AGES.sql   # Source Text File(s)

Readers:
- TEXTLINE_1: TEXTLINE from $(SourceDataset_TEXTLINE)

Writers:
- POSTGRES_1: POSTGRES to $(DestDataset_POSTGRES_3)
- POSTGRES_2: POSTGRES to $(DestDataset_POSTGRES_4)

Note: SQL file from drawdb
text_line (reader TEXTLINE_1)
    attributes: text_line_data buffer
    -> ListBuilder
ListBuilder
    GROUP_BY = fme_feature_type
    LIST_ATTRS_TO_INCLUDE = text_line_data
    LIST_NAME = _list
    -> ListConcatenator_2
ListConcatenator_2
    DROP_EMPTY_PARTS = No
    LIST_ATTR = _list{}.text_line_data
    VAL_ATTR = _concatenated
    -> AttributeManager_2
AttributeManager_2
    ATTR_TABLE:
      SET_TO ett (varchar(200)) = @ReplaceString(@Value(_concatenated),	,
         ,caseSensitive=TRUE)
      SET_TO två (varchar(200)) = @ReplaceString(@Value(ett),agestest.,agestest".",caseSensitive=TRUE)
      SET_TO tre (varchar(200)) = @ReplaceString(@Value(två),common.,common".",caseSensitive=TRUE)
      SET_TO fyra (varchar(200)) = @ReplaceString(@Value(tre),BLOB,geometry,caseSensitive=TRUE)
      SET_TO sql_create (varchar(200)) = FME_SQL_DELIMITER ;
        @Value(fyra)
    -> FeatureMerger [REQUESTOR]
Creator
    GEOMTYPE = Geometry Object
    NUM = 1
    CREATED -> SystemCaller_3
Note: drop db
SystemCaller_3
    CMD = ""C:/Program Files/PostgreSQL/$(dbversion)/bin/psql.exe" -h $(server)  -p $(port) -U $(user) -c "DROP DATABASE IF EXISTS ages_test WITH (FORCE)""
    -> SystemCaller_2
Note: create db
SystemCaller_2
    CMD = ""C:/Program Files/PostgreSQL/$(dbversion)/bin/psql.exe" -h $(server)  -p $(port) -U $(user) -c "CREATE DATABASE  ages_test WITH TEMPLATE = ages_template ENCODING = 'UTF8'""
    -> SQLExecutor [INITIATOR]
Note: create schemans
SQLExecutor
    COMBINE_ATTRS_OPTIONS = RESULT_ONLY
    COMBINE_GEOM_OPTIONS = QUERY_ONLY
    DATASET = ages_test
    FORMAT = POSTGIS
    OUTPUT_FEATURES = BASED_ON_CONNECTIONS
    POSTGIS_CREATE_FEATURE_TABLES_FROM_DATA = Yes
    POSTGIS_DISABLE_COLLECTION_SPLITTING = yes
    POSTGIS_HOST = $(server)
    POSTGIS_PASSWORD =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
    POSTGIS_PORT = $(port)
    POSTGIS_QUERY_FEATURE_TYPES_FOR_MERGE_FILTERS = Yes
    POSTGIS_READ_TIME_WITH_TIMEZONE = Yes
    POSTGIS_SSLMODE = prefer
    POSTGIS_USER_NAME = postgres
    POSTGIS_USE_TRUE_POSTGIS_TYPES = yes
    SQL_STATEMENT:
      FME_SQL_DELIMITER ;
      CREATE SCHEMA common;
      CREATE SCHEMA agestest;
    COMBINE_ATTRS = Result Attributes Only
    COMBINE_GEOM = Initiator Geometry Only
    OUTPUT_FEATURES_DISPLAY = Schema and Data Features
    INITIATOR -> FeatureMerger [SUPPLIER]
    <REJECTED> -> Terminator
FeatureMerger
    ATTR_ACCUM_MODE = Merge Supplier
    ATTR_CONFLICT_RES_LOOKUP = REQUESTOR_IF_CONFLICT
    IGNORE_NULLS = No
    JOIN_KEYS = 1 1 AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> SQLExecutor_2 [INITIATOR]
Note: create tables
SQLExecutor_2
    COMBINE_ATTRS_OPTIONS = RESULT_ONLY
    COMBINE_GEOM_OPTIONS = QUERY_ONLY
    DATASET = ages_test
    FORMAT = POSTGIS
    OUTPUT_FEATURES = BASED_ON_CONNECTIONS
    POSTGIS_CREATE_FEATURE_TABLES_FROM_DATA = Yes
    POSTGIS_DISABLE_COLLECTION_SPLITTING = yes
    POSTGIS_HOST = $(server)
    POSTGIS_PASSWORD =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
    POSTGIS_PORT = $(port)
    POSTGIS_QUERY_FEATURE_TYPES_FOR_MERGE_FILTERS = Yes
    POSTGIS_READ_TIME_WITH_TIMEZONE = Yes
    POSTGIS_SSLMODE = prefer
    POSTGIS_USER_NAME = postgres
    POSTGIS_USE_TRUE_POSTGIS_TYPES = yes
    SQL_STATEMENT = @Value(sql_create)
    COMBINE_ATTRS = Result Attributes Only
    COMBINE_GEOM = Initiator Geometry Only
    OUTPUT_FEATURES_DISPLAY = Schema and Data Features
    INITIATOR -> FeatureReader [INITIATOR]
    INITIATOR -> FeatureReader_2 [INITIATOR]
    INITIATOR -> FeatureReader_3 [INITIATOR]
Note: från excel common tabeller
FeatureReader_3
    ATTRIBUTES = format,"id,namn,beskrivning",koordsys,"id,namn,epsg,sys_uri",organisation,"id,namn,org_uri"
    ATTR_ACCUM_MODE = Only Use Result
    CLIP_TO_ENVELOPE = NO
    COMBINE_GEOM = Use Result
    DATASET = $(FME_MF_DIR_ENCODED)common_tabeller.xlsx
    FEATURETYPES = format koordsys organisation
    FORMAT = XLSXR
    INITIATOR_FIRST_OUTPUT = default
    INPUT_PORT_INITIATOR_CONNECTED = CONNECTED
    INTERACT = NONE
    ORDER_RESULTS = No
    OUTPUT_ADD_SCHEMA_ATTRIBUTES = NO
    OUTPUT_FEATURES_DISPLAY = Schema and Data Features
    OUTPUT_USE_SCHEMA_CACHE = YES
    READER_BEHAVIOR = Constraint Parameters
    XLSXR_ALLOW_DOLLAR_SIGNS = YES
    XLSXR_APPLY_FILTERS = No
    XLSXR_CASE_SENSITIVE_FEATURE_TYPES = YES
    XLSXR_CONFIGURATION_DATASET = $(FME_MF_DIR)common_tabeller.xlsx
    XLSXR_CREATE_FEATURE_TABLES_FROM_DATA = Yes
    XLSXR_EXCEL_COL_NAMES = YES
    XLSXR_EXPANDED_DATES_SCANNING = No
    XLSXR_EXPAND_MERGED_CELLS = Yes
    XLSXR_FORCE_DATETIME = NO
    XLSXR_QUERY_FEATURE_TYPES_FOR_MERGE_FILTERS = Yes
    XLSXR_READ_BLANK_AS = Null
    XLSXR_READ_FORM_CONTROLS = NONE
    XLSXR_READ_RASTER_MODE = None
    XLSXR_REPLACE_ONLY_NEWLINES_CARRIAGE_RETURNS = YES
    XLSXR_SCAN_FOR_GEOMETRIC_TYPES = Yes
    XLSXR_SCAN_MAX_FEATURES = 1000
    XLSXR_SCHEMA = koordsys,0,id,number,2,0,,1,namn,char,24,,,2,epsg,number,4,0,,3,sys_uri,char,42,,,1,,,,NO,NO,1,C:\Github\kix\divFME\ages\nya_ages\common_tabeller.xlsx,"0,0,3,47",,NO,NO,1,2:,format,0,id,number,1,0,,1,namn,char,19,,,2,beskrivning,string,,,,1,,,,NO,NO,1,,"0,0,2,5",,NO,NO,1,2:,organisation,0,id,number,3,0,,1,namn,char,70,,,2,org_uri,string,,,,1,,,,NO,NO,1,,"0,0,2,115",,NO,NO,1,2:
    XLSXR_SCHEMA_HANDLING_REVISION = 2
    XLSXR_SKIP_EMPTY_ATTRS = No
    XLSXR_SKIP_EMPTY_ROWS = YES
    XLSXR_STRIP_SHEETNAME_SPACES = YES
    XLSXR_TABLELIST = koordsys format organisation
    XLSXR_TRIM_ATTR_NAME_WHITESPACE = Yes
    XLSXR_USE_CUSTOM_SCHEMA = YES
    format -> Tester
    koordsys -> Tester_2
    organisation -> Tester_3
Tester
    BOOL_OP = OR
    TEST_CLAUSE = TEST id ATTRIBUTE_HAS_A_VALUE ""
    TEST_MODE = TEST
    PASSED -> format (writer POSTGRES_1)
format (writer POSTGRES_1)
    attributes: id int2, namn varchar(19), beskrivning varchar
Tester_2
    BOOL_OP = OR
    TEST_CLAUSE = TEST id ATTRIBUTE_HAS_A_VALUE ""
    TEST_MODE = TEST
    PASSED -> koordsys (writer POSTGRES_1)
koordsys (writer POSTGRES_1)
    attributes: id int2, namn varchar(24), epsg int2, sys_uri varchar(42)
Tester_3
    BOOL_OP = OR
    TEST_CLAUSE = TEST id ATTRIBUTE_HAS_A_VALUE ""
    TEST_MODE = TEST
    PASSED -> organisation (writer POSTGRES_1)
organisation (writer POSTGRES_1)
    attributes: id int4,PrimaryKey, org_uri text, namn text
Note: från riktiga ages
FeatureReader
    ATTRIBUTES = common.rapport_uppdrag,"uuid_uppdrag,uuid_rapport,rapport,rapport_info"
    ATTR_ACCUM_MODE = Only Use Result
    COMBINE_GEOM = Use Result
    DATASET = uuc-srv390_ages_5434
    FEATURETYPES = common.rapport_uppdrag
    FORMAT = POSTGRES
    INITIATOR_FIRST_OUTPUT = default
    INPUT_PORT_INITIATOR_CONNECTED = CONNECTED
    ORDER_RESULTS = No
    OUTPUT_ADD_SCHEMA_ATTRIBUTES = NO
    OUTPUT_FEATURES_DISPLAY = Schema and Data Features
    OUTPUT_USE_SCHEMA_CACHE = YES
    POSTGRES_CREATE_FEATURE_TABLES_FROM_DATA = Yes
    POSTGRES_FEATURES_PER_FETCH = 10000
    POSTGRES_NAMED_CONNECTION = uuc-srv390_ages_5434
    POSTGRES_QUERY_FEATURE_TYPES_FOR_MERGE_FILTERS = Yes
    POSTGRES_READ_TIME_WITH_TIMEZONE = Yes
    POSTGRES_SCHEMAS_FOR_TABLE_LISTING = common
    READER_BEHAVIOR = SELECTFEATTYPES
    common.rapport_uppdrag -> rapport_uppdrag (writer POSTGRES_1)
rapport_uppdrag (writer POSTGRES_1)
    attributes: uuid_uppdrag varchar(36), uuid_rapport varchar(36), rapport varchar(78), rapport_info varchar(69)
Note: från riktiga ages
FeatureReader_2
    ATTRIBUTES = common.sverige_buff5000,"landskap,kommentar,skala,_area_utan_buffer"
    ATTR_ACCUM_MODE = Only Use Result
    CLIP_TO_ENVELOPE = NO
    COMBINE_GEOM = Use Result
    DATASET = uuc-srv390_ages_5434
    FEATURETYPES = common.sverige_buff5000
    FORMAT = POSTGIS
    GEOMETRY_TYPES = common.sverige_buff5000,"""geom,fme_area,fme_collection,fme_line,fme_point,fme_surface"""
    INITIATOR_FIRST_OUTPUT = default
    INPUT_PORT_INITIATOR_CONNECTED = CONNECTED
    INTERACT = NONE
    ORDER_RESULTS = No
    OUTPUT_ADD_SCHEMA_ATTRIBUTES = NO
    OUTPUT_FEATURES_DISPLAY = Schema and Data Features
    OUTPUT_USE_SCHEMA_CACHE = YES
    POSTGIS_CREATE_FEATURE_TABLES_FROM_DATA = Yes
    POSTGIS_DISABLE_COLLECTION_SPLITTING = yes
    POSTGIS_FEATURES_PER_FETCH = 10000
    POSTGIS_NAMED_CONNECTION = uuc-srv390_ages_5434
    POSTGIS_QUERY_FEATURE_TYPES_FOR_MERGE_FILTERS = Yes
    POSTGIS_READ_TIME_WITH_TIMEZONE = Yes
    POSTGIS_SCHEMAS_FOR_TABLE_LISTING = common
    POSTGIS_USE_SEARCH_ENVELOPE = NO
    POSTGIS_USE_TRUE_POSTGIS_TYPES = yes
    READER_BEHAVIOR = SELECTFEATTYPES
    common.sverige_buff5000 -> sverige_buff5000 (writer POSTGRES_2)
sverige_buff5000 (writer POSTGRES_2)
    attributes: landskap varchar(254), kommentar varchar(150), skala varchar(100), _area_utan_buffer float8
Terminator
    MESSAGE = Translation Terminated
