FME workspace saveSverige2postgis.fmw

Parameters:
- SourceDataset_SHAPEFILE = \\argos.storage.uu.se\MyFolder$\krima354\kicki_arbetsfiler\GETdata\landskap_frDaniel\svelandskap_2010_rev_granser.shp   # Source Esri Shapefile(s)
- DestDataset_POSTGIS = ages-teat@uuc-srv5432   # Connection

Readers:
- SHAPEFILE_1: SHAPEFILE from $(SourceDataset_SHAPEFILE) in EPSG:3006

Writers:
- POSTGIS_1: POSTGIS to $(DestDataset_POSTGIS)

svelandskap_2010_rev_granser (reader SHAPEFILE_1)
    attributes: LANDSKAP varchar(254), ID number(16,0), KOMMENTAR varchar(150), SKALA varchar(100), AREA_METER double, PERIMETER_ double, HECTARES double
    -> Dissolver
Dissolver
    ACCUM_INPUT_ATTRS = Use Attributes From One Feature
    CLEANING_TOLERANCE = Automatic
    CONNECT_Z_MODE = First Wins
    DEAGGREGATE_INPUT = Yes
    AREA -> DonutHoleExtractor
DonutHoleExtractor
    DEAGGREGATE_INPUT = Yes
    OUTERSHELL -> AreaCalculator
AreaCalculator
    AREA_ATTR = _area
    AREA_TYPE = Plane Area
    MULT = 1
    -> TestFilter
TestFilter
    DEFAULT_VALUE = <UNFILTERED>
    PASSED_TEST_GROUP_OUTPUT = FIRST
    TEST_LIST:
      "BOOL_OP,OR,COMPOSITE_TEST,""""""1 OR 2 OR 3"""""",TEST_CLAUSE,TEST @Value(_area) > 466942792496
      TEST @Value(LANDSKAP) = Gotland
      TEST @Value(LANDSKAP) = Öland",sverige_poly,"BOOL_OP,OR,COMPOSITE_TEST,""""""1"""""",TEST_CLAUSE,TEST @Value(LANDSKAP) = Gotland",@Value(LANDSKAP) = Gotland
    sverige_poly -> Bufferer
Bufferer
    ANGLE = 22.5
    CAP_STYLE = Arc
    CORNER_STYLE = Arc
    MODE = AREA
    OFFSET = 5000
    OFFSET_UNITS = METERS
    PRECISION = APPROX
    BUFFERED -> AttributeManager
AttributeManager
    ATTR_TABLE:
      SET_TO LANDSKAP = FME_CONDITIONAL:DEFAULT_VALUE'_FME_NO_OP_'BOOL_OP;OR;COMPOSITE_TEST;1;TEST @Value(LANDSKAP) = Lappland'SVERIGE'FME_NUM_CONDITIONS2___
      REMOVE ID
      REMOVE AREA_METER
      REMOVE PERIMETER_
      REMOVE HECTARES
      RENAME_SET_VALUE _area > _area_utan_buffer
    -> sverige_buff5000 (writer POSTGIS_1)
sverige_buff5000 (writer POSTGIS_1)
    attributes: landskap varchar(254), kommentar varchar(150), skala varchar(100), _area_utan_buffer float8
