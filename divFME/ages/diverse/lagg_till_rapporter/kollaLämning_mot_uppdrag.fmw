FME workspace kollaLämning_mot_uppdrag.fmw

Parameters:
- SourceDataset_OGCGEOPACKAGE = C:\ny_slask\GIS-data\lämningar_sverige (3).gpkg   # GeoPackage File
- SourceDataset_OGCGEOPACKAGE_5 = C:\ny_slask\GIS-data\arkeologiska_uppdrag_grävda_ytor_sverige (3).gpkg   # GeoPackage File
- SourceDataset_OGCGEOPACKAGE_4 = C:\ny_slask\GIS-data\lämningar_sverige (3).gpkg   # GeoPackage File

Readers:
- OGCGEOPACKAGE_1: OGCGEOPACKAGE from $(SourceDataset_OGCGEOPACKAGE)
- OGCGEOPACKAGE_2: OGCGEOPACKAGE from $(SourceDataset_OGCGEOPACKAGE_5)
- OGCGEOPACKAGE_3: OGCGEOPACKAGE from $(SourceDataset_OGCGEOPACKAGE_4)

arkeologiska_uppdrag_grävda_ytor_sverige_linestring (reader OGCGEOPACKAGE_2)
    attributes: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
arkeologiska_uppdrag_grävda_ytor_sverige_point (reader OGCGEOPACKAGE_2)
    attributes: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
arkeologiska_uppdrag_grävda_ytor_sverige_polygon (reader OGCGEOPACKAGE_2)
    attributes: id text(255), uppdragsnummer text(9), beslutande_myndighet text(255), beslutsdatum date, diarienummer text(255), uppdragstyp text(255), utforande_organisation text(255), nollresultat text(9), url text(255), status text(255), lan text, kommun text, socken text, fid int,PrimaryKey
    -> SpatialRelator [Supplier]
Creator
    GEOMTYPE = Geometry Object
    NUM = 1
    CREATED -> HTTPCaller
    CREATED -> HTTPCaller_2
    CREATED -> HTTPCaller_3
    CREATED -> PythonCaller
Note: dokumentation för ett uppdrag
Note: https://app.raa.se/open/fornsok/lamning/0caa9d04-05c3-413d-a4e3-ab7b17214a87 / https://arkivsok.raa.se/results?lamningsnummer=L2018:754&searchtype=filter&page=0&pagesize=100
HTTPCaller
    CLIENT_CERTIFICATE_TYPE = NONE
    CONNECTION_TIMEOUT_LENGTH = 60
    ERROR_ATTR = _error
    FOLLOW_REDIRECTS = FOLLOW_WITH_GET
    HTTP_METHOD = GET
    INPUT_PORT_CONNECTED = CONNECTED
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://pub.raa.se/dokumentation/bc522862-f373-4eae-ae18-2b6ad94ceef5
    TEST_DIALOG_PARAMETERS_FOR_RESPONSE = authConnection;<Unused> authEnabled;false authMethod;<Unused> authPassword;<Unused> authUsername;<Unused> contentType;<Unused> method;GET multipartContentType;<Unused> requestUrl;https://pub.raa.se/dokumentation/bc522862-f373-4eae-ae18-2b6ad94ceef5 uploadData;<Unused> verifySslCert;Yes version;HTTP_2
    TEST_DIALOG_RESPONSE_PREVIEW = Specify test values and send test request, to view test response.
    TEST_DIALOG_RESPONSE_STATUS = Specify test values and send test request, to view test response.
    TRANSFER_TIMEOUT_LENGTH = 90
    USE_COOKIES = No
    VERIFY_SSL_CERTIFICATES = Yes
HTTPCaller_2
    CLIENT_CERTIFICATE_TYPE = NONE
    CONNECTION_TIMEOUT_LENGTH = 60
    ERROR_ATTR = _error
    FOLLOW_REDIRECTS = FOLLOW_WITH_GET
    HTTP_METHOD = GET
    INPUT_PORT_CONNECTED = CONNECTED
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://arkivsok.raa.se/results?lamningsnummer=L2018:754&searchtype=filter&page=0&pagesize=100
    TRANSFER_TIMEOUT_LENGTH = 90
    USE_COOKIES = No
    VERIFY_SSL_CERTIFICATES = Yes
HTTPCaller_3
    ADDITIONAL_URL_PARAMETERS:
      query;PREFIX soch: <http://kulturarvsdata.se/ksamsok#>

      SELECT ?lämning WHERE {{
        ?lämning soch:identifier ?id .
        ?id soch:value "{l_number}" .
      }} format;application/sparql+json
    CLIENT_CERTIFICATE_TYPE = NONE
    CONNECTION_TIMEOUT_LENGTH = 60
    ERROR_ATTR = _error
    FOLLOW_REDIRECTS = FOLLOW_WITH_GET
    HTTP_METHOD = GET
    INPUT_PORT_CONNECTED = CONNECTED
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://sparql.kulturarvsdata.se/
    TEST_DIALOG_PARAMETERS_FOR_RESPONSE:
      authConnection;<Unused> authEnabled;false authMethod;<Unused> authPassword;<Unused> authUsername;<Unused> contentType;<Unused> method;GET multipartContentType;<Unused> queryParams:format;application/sparql+json queryParams:query;PREFIX soch: <http://kulturarvsdata.se/ksamsok#>

      SELECT ?lämning WHERE {{
        ?lämning soch:identifier ?id .
        ?id soch:value "{l_number}" .
      }} requestUrl;https://sparql.kulturarvsdata.se/ uploadData;<Unused> verifySslCert;Yes version;HTTP_2
    TEST_DIALOG_RESPONSE_PREVIEW = <!DOCTYPE html> <html lang="sv">   <head>     <meta charset="utf-8" />     <meta name="viewport" content="width=device-width, initial-scale=1" />     <link href="https://fonts.googleapis.com/css?family=Source+Sans+Pro:400" rel="stylesheet" />     <link rel="stylesheet" href="/assets/styles.css" />      <!-- generics -->     <link rel="icon" href="assets/images/favicon/raa-favicon-32.png" sizes="32x32" />     <link rel="icon" href="assets/images/favicon/raa-favicon-57.png" sizes="57x57" />     <link rel="icon" href="assets/images/favicon/raa-favicon-76.png" sizes="76x76" />     <link rel="icon" href="assets/images/favicon/raa-favicon-96.png" sizes="96x96" />     <link rel="icon" href="assets/images/favicon/raa-favicon-128.png" sizes="128x128" />     <link rel="icon" href="assets/images/favicon/raa-favicon-228.png" sizes="228x228" />      <!-- Android -->     <link rel="shortcut icon" sizes="196x196" href="assets/images/favicon/raa-favicon-196.png" />      <!-- iOS -->     <link rel="apple-touch-icon" href="assets/images/favicon/raa-favicon-120.png" sizes="120x120" />     <link rel="apple-touch-icon" href="assets/images/favicon/raa-favicon-152.png" sizes="152x152" />     <link rel="apple-touch-icon" href="assets/images/favicon/raa-favicon-180.png" sizes="180x180" />      <!-- Windows 8 IE 10-->     <meta name="msapplication-TileColor" content="#FFFFFF" />     <meta name="msapplication-TileImage" content="assets/images/favicon/raa-favicon-144.png" />     <title>Riksantikvarieämbetets digitala tjänster</title>   </head>    <body>     <header>       <img class="header-logo" src="/assets/images/RAA_logo.svg" alt="RAÄ logo" />     </header>      <main>       <h1 class="services-title">Digitala tjänster</h1>        <div class="container">         <a class="service-card rounded-bottom" rel="noopener noreferrer" href="/open/arkivsok">           <div class="text-content">             <span class="title">Arkivsök</span>             <p>I Arkivsök söker du i innehållet i Riksantikvarieämbetets e-arkiv. Exempelvis kan du söka efter               fotografier, ritningar, publikationer och databaser. Arkivsök är öppen för alla.</p>           </div>         </a>          <div>           <a class="service-card" rel="noopener noreferrer" href="/open/bebyggelse">             <div class="text-content">               <span class="title">Bebyggelseregistret</span>               <p>I Bebyggelseregistret finns information om det byggda kulturarvet. Tjänsten är öppen för alla.</p>               <p>Den som är yrkesverksam kan registrera bebyggelse med hjälp av en personlig behörighet.</p>             </div>           </a>            <div class="card-footer">             <a class="external-link"                target="_blank"                rel="noopener noreferrer"                href="https://www.raa.se/hitta-information/bebyggelseregistret/registrera-i-bebyggelseregistret/soka-behorighet/">               Läs mer om behörigheter             </a>           </div>         </div>          <a class="service-card rounded-bottom" rel="noopener noreferrer" href="/open/fornsok">           <div class="text-content">             <span class="title">Fornsök</span>             <p>Fornsök innehåller information om alla kända registrerade fornlämningar och övriga kulturhistoriska lämningar i Sverige. Här finns även information om arkeologiska uppdrag. Fornsök är öppen för alla.</p>           </div>         </a>          <div>           <a class="service-card" rel="noopener noreferrer" href="/id/secure/fornreg">             <div class="text-content">               <span class="title">Fornreg</span>               <p>Fornreg är ett verktyg för registrering av information om arkeologiska uppdrag och lämningar.</p>               <p>Den som är yrkesverksam kan registrera information med hjälp av en personlig behörighet.</p>             </div>           </a>            <div class="card-footer">             <a class="external-link"                target="_blank"                rel="noopener noreferrer"                href="https://www.raa.se/hitta-information/fornreg/behorigheter-i-fornreg/">               Läs mer om behörigheter             </a>           </div>         </div>          <a class="service-card rounded-bottom" rel="noopener noreferrer" href="/open/runor">           <div class="text-content">             <span class="title">Runor</span>             <p>Söktjänsten Runor är en ny digital forskningsplattform som ska tillgängliggöra ungefär 7 000 inskrifter med rapporter och bilder från olika databaser, institutioner och samlingar.</p>           </div>         </a>          <a class="service-card rounded-bottom" rel="noopener noreferrer" href="https://pub.raa.se">           <div class="text-content">             <span class="title">Öppna data-portalen</span>             <p>På Öppna data-portalen samlar vi Riksantikvarieämbetets geodatatjänster. Den geodata som vi erbjuder är öppen för alla.</p>           </div>         </a>       </div>     </main>      <script>       if (window.location.host.indexOf('testraa.se') !== -1) {         const cardFooterElements = document.getElementsByClassName('card-footer');         Array.prototype.forEach.call(cardFooterElements, function(el) {           const link = document.createElement('a');           link.className = 'external-link';           link.rel = "noopener noreferrer";           link.href = "/id/selfservice";           link.textContent = 'Administrera behörigheter';           el.append(link)         });       }     </script>     <script src="/assets/scripts.js" type="text/javascript"></script>   </body> </html>
    TEST_DIALOG_RESPONSE_STATUS:
      HTTP/1.1 200 OK
      Download Size: 5681 bytes
      Total Transfer Time: 181 ms
    TRANSFER_TIMEOUT_LENGTH = 90
    USE_COOKIES = No
    VERIFY_SSL_CERTIFICATES = Yes
PythonCaller
    INPUT_PORT_CONNECTED = CONNECTED
    PYTHONSOURCE:
      import fme
      from fme import BaseTransformer
      import fmeobjects


      class FeatureProcessor(BaseTransformer):
          """Template Class Interface:
          When using this class, make sure its name is set as the value of the 'Class to Process Features'
          transformer parameter.

          This class inherits from 'fme.BaseTransformer'. For full details of this class, its methods, and
          expected usage, see https://docs.safe.com/fme/html/fmepython/api/fme.html#fme.BaseTransformer.
          """

          def __init__(self):
              """Base constructor for class members."""
              pass

          def has_support_for(self, support_type: int):
              """This method is called by FME to determine if the PythonCaller supports Bulk mode,
              which allows for significant performance gains when processing large numbers of features.
              """
              return support_type == fmeobjects.FME_SUPPORT_FEATURE_TABLE_SHIM

          def input(self, feature: fmeobjects.FMEFeature):
              """This method is called for each feature which enters the PythonCaller."""
              self.pyoutput(feature, output_tag="PYOUTPUT")

          def close(self):
              """This method is called once all the FME Features have been processed from input()."""
              pass

          def process_group(self):
              """This method is called by FME for each group when group processing mode is enabled."""
              pass

          def reject_feature(self, feature: fmeobjects.FMEFeature, code: str, message: str):
              """This method can be used to output a feature to the <Rejected> port."""
              feature.setAttribute("fme_rejection_code", code)
              feature.setAttribute("fme_rejection_message", message)
              self.pyoutput(feature, output_tag="<Rejected>")
    PYTHONSYMBOL = FeatureProcessor
lamning (reader OGCGEOPACKAGE_1)
    attributes: uuid text, lamningsnummer text(11), raa_nummer text(300), lamningstyp text(255), url text, beskrivning text, publicerad_av text(255), publiceringsdatum datetime, uttagsdatum date, antikvariskbedomning text(255), antikvariskbedomning_motivering text, aktualitetstatus text(255), skadestatus text(255), undersokningsstatus text(255), placering text(255), terrang text, orientering text, tradition text, lamningsnamn text(300), lan text, kommun text, socken text, inspire_ruin boolean, fid int,PrimaryKey
    -> FeatureMerger [SUPPLIER]
linestring (reader OGCGEOPACKAGE_3)
    attributes: lamning_uuid text, geometrinummer text, fid int,PrimaryKey
    -> Tester
point (reader OGCGEOPACKAGE_3)
    attributes: lamning_uuid text, geometrinummer text, fid int,PrimaryKey
    -> Tester
polygon (reader OGCGEOPACKAGE_3)
    attributes: lamning_uuid text, geometrinummer text, fid int,PrimaryKey
    -> Tester
Tester
    BOOL_OP = OR
    TEST_CLAUSE = TEST 1 = 1
    TEST_MODE = TEST
    PASSED -> FeatureMerger [REQUESTOR]
FeatureMerger
    ATTR_ACCUM_MODE = Merge Supplier
    ATTR_CONFLICT_RES_LOOKUP = REQUESTOR_IF_CONFLICT
    IGNORE_NULLS = No
    JOIN_KEYS = @Value(lamning_uuid) @Value(uuid) AUTO
    MERGE_TYPE_VAL = GEOM_AND_ATTRS
    PROCESS_DUPS = NO
    REJECT_NULL_MISSING_KEYS = No
    SUPPLIERS_FIRST = No
    ATTR_CONFLICT_RES = Use Requestor
    MERGE_TYPE = Attributes and Geometry
    MERGED -> SpatialRelator [Requestor]
SpatialRelator
    AGGREGATE_HANDLING = Yes
    CALC_CARD = No
    CURVE_BOUNDARY_RULE_PARAM = Default Rule
    LIST_NAME = _relationships
    PREDICATES = WITHIN CONTAINS EQUALS INTERSECTS TOUCHES
    SUCCESS_ATTR = _related_suppliers
