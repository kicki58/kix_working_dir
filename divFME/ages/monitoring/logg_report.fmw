FME workspace logg_report.fmw

Parameters:
- Start_date = 20250101   # Start date
- end_date = 20251231   # End date
- PostgreSQL_CONNECTION = postgres@ages-monitoring_uuc-srv390_5434   # Connection
- DestDataset_XLSXW = C:\ny_slask\monitoring2025.xlsx   # Destination Microsoft Excel File

Writers:
- XLSXW_1: XLSXW to $(DestDataset_XLSXW)

Note: SQLCreator_6 : Result
Junction_2
    -> TestFilter_2
Note: SQLCreator_6 : Result
Junction_4
    -> TestFilter

Bookmark: geoserver
Note: antal/typ requests
SQLCreator
    DATASET = $(PostgreSQL_CONNECTION)
    EXPOSED_ATTRIBUTE_LIST = operation,count
    FORMAT = POSTGRES
    OUTPUT_FEATURES = DATA_ONLY
    POSTGRES_CREATE_FEATURE_TABLES_FROM_DATA = Yes
    POSTGRES_NAMED_CONNECTION = $(PostgreSQL_CONNECTION)
    POSTGRES_QUERY_FEATURE_TYPES_FOR_MERGE_FILTERS = Yes
    POSTGRES_READ_TIME_WITH_TIMEZONE = Yes
    SQL_STATEMENT:
      FME_SQL_DELIMITER ;
      SELECT operation, count(operation)
      FROM logs.geoserver
      where starttime >= to_date('$(Start_date)', 'YYYYMMDD') AND endtime < to_date('$(end_date)', 'YYYYMMDD')
      group by operation
    RESULT -> geoserver_request (writer XLSXW_1)
geoserver_request (writer XLSXW_1)
    attributes: operation string(20), count string(20)
Note: host
SQLCreator_4
    DATASET = $(PostgreSQL_CONNECTION)
    EXPOSED_ATTRIBUTE_LIST = host,count
    FORMAT = POSTGRES
    OUTPUT_FEATURES = DATA_ONLY
    POSTGRES_CREATE_FEATURE_TABLES_FROM_DATA = Yes
    POSTGRES_NAMED_CONNECTION = $(PostgreSQL_CONNECTION)
    POSTGRES_QUERY_FEATURE_TYPES_FOR_MERGE_FILTERS = Yes
    POSTGRES_READ_TIME_WITH_TIMEZONE = Yes
    SQL_STATEMENT:
      FME_SQL_DELIMITER ;
      SELECT host, count(host)
      FROM logs.geoserver
      where starttime >= to_date('$(Start_date)', 'YYYYMMDD') AND endtime < to_date('$(end_date)', 'YYYYMMDD')
      group by host
    RESULT -> geoserver_hosts (writer XLSXW_1)
geoserver_hosts (writer XLSXW_1)
    attributes: host string(20), count string(20)
Note: resources
SQLCreator_5
    DATASET = $(PostgreSQL_CONNECTION)
    EXPOSED_ATTRIBUTE_LIST = resources,count
    FORMAT = POSTGRES
    OUTPUT_FEATURES = DATA_ONLY
    POSTGRES_CREATE_FEATURE_TABLES_FROM_DATA = Yes
    POSTGRES_NAMED_CONNECTION = $(PostgreSQL_CONNECTION)
    POSTGRES_QUERY_FEATURE_TYPES_FOR_MERGE_FILTERS = Yes
    POSTGRES_READ_TIME_WITH_TIMEZONE = Yes
    SQL_STATEMENT:
      FME_SQL_DELIMITER ;
      SELECT resources, count(resources)
      FROM logs.geoserver
      where starttime >= to_date('$(Start_date)', 'YYYYMMDD') AND endtime < to_date('$(end_date)', 'YYYYMMDD')
      group by resources
    RESULT -> geoserver_recources (writer XLSXW_1)
geoserver_recources (writer XLSXW_1)
    attributes: resources string(20), count string(20)

Bookmark: iiis
Note: antal method
SQLCreator_12
    DATASET = $(PostgreSQL_CONNECTION)
    EXPOSED_ATTRIBUTE_LIST = count,cs_method
    FORMAT = POSTGRES
    OUTPUT_FEATURES = DATA_ONLY
    POSTGRES_CREATE_FEATURE_TABLES_FROM_DATA = Yes
    POSTGRES_NAMED_CONNECTION = $(PostgreSQL_CONNECTION)
    POSTGRES_QUERY_FEATURE_TYPES_FOR_MERGE_FILTERS = Yes
    POSTGRES_READ_TIME_WITH_TIMEZONE = Yes
    SQL_STATEMENT:
      FME_SQL_DELIMITER ;
       SELECT count(cs_method) AS count, cs_method
         FROM logs.iis
          WHERE
            date >= to_date('$(Start_date)', 'YYYYMMDD') AND date < to_date('$(end_date)', 'YYYYMMDD')
            GROUP BY  cs_method;
    RESULT -> iis_request (writer XLSXW_1)
iis_request (writer XLSXW_1)
    attributes: count string(20), cs_method string(20)
Note: antal nedladdningar
SQLCreator_2
    DATASET = $(PostgreSQL_CONNECTION)
    EXPOSED_ATTRIBUTE_LIST = antal_nedladdningar
    FORMAT = POSTGRES
    OUTPUT_FEATURES = DATA_ONLY
    POSTGRES_CREATE_FEATURE_TABLES_FROM_DATA = Yes
    POSTGRES_NAMED_CONNECTION = $(PostgreSQL_CONNECTION)
    POSTGRES_QUERY_FEATURE_TYPES_FOR_MERGE_FILTERS = Yes
    POSTGRES_READ_TIME_WITH_TIMEZONE = Yes
    SQL_STATEMENT:
      FME_SQL_DELIMITER ;
       SELECT count(cs_uri_stem) AS antal_nedladdningar
         FROM logs.iis
        WHERE cs_uri_stem::text ~~ '%.gpkg%'::text
          AND  date >= to_date('$(Start_date)', 'YYYYMMDD') AND date < to_date('$(end_date)', 'YYYYMMDD');
    RESULT -> iis_nedladdning (writer XLSXW_1)
iis_nedladdning (writer XLSXW_1)
    attributes: antal_nedladdningar string(20)
Note: antal nedladdningar per gpkg
SQLCreator_3
    DATASET = $(PostgreSQL_CONNECTION)
    EXPOSED_ATTRIBUTE_LIST = count,cs_uri_stem
    FORMAT = POSTGRES
    OUTPUT_FEATURES = DATA_ONLY
    POSTGRES_CREATE_FEATURE_TABLES_FROM_DATA = Yes
    POSTGRES_NAMED_CONNECTION = $(PostgreSQL_CONNECTION)
    POSTGRES_QUERY_FEATURE_TYPES_FOR_MERGE_FILTERS = Yes
    POSTGRES_READ_TIME_WITH_TIMEZONE = Yes
    SQL_STATEMENT:
      FME_SQL_DELIMITER ;
       SELECT count(cs_uri_stem) AS count, cs_uri_stem
         FROM logs.iis
        WHERE cs_uri_stem::text ~~ '%.gpkg%'::text AND  date >= to_date('$(Start_date)', 'YYYYMMDD') AND date < to_date('$(end_date)', 'YYYYMMDD')
        GROUP BY cs_uri_stem;
    RESULT -> AttributeManager_3
AttributeManager_3
    ATTR_TABLE = SET_TO gpkg (varchar(200)) = @TrimLeft(@Value(cs_uri_stem),/gpkg/ )
    -> AttributeRemover
AttributeRemover
    REMOVE_ATTRS = cs_uri_stem
    -> iis_nedladdning_per_gpkg (writer XLSXW_1)
iis_nedladdning_per_gpkg (writer XLSXW_1)
    attributes: count number(20), gpkg string(200)
Note: cs_user_agent_
SQLCreator_6
    DATASET = $(PostgreSQL_CONNECTION)
    EXPOSED_ATTRIBUTE_LIST = count,cs_user_agent_
    FORMAT = POSTGRES
    OUTPUT_FEATURES = DATA_ONLY
    POSTGRES_CREATE_FEATURE_TABLES_FROM_DATA = Yes
    POSTGRES_NAMED_CONNECTION = $(PostgreSQL_CONNECTION)
    POSTGRES_QUERY_FEATURE_TYPES_FOR_MERGE_FILTERS = Yes
    POSTGRES_READ_TIME_WITH_TIMEZONE = Yes
    SQL_STATEMENT:
      FME_SQL_DELIMITER ;
       SELECT count(cs_user_agent_) AS count, cs_user_agent_
         FROM logs.iis
        WHERE   date >= to_date('$(Start_date)', 'YYYYMMDD') AND date < to_date('$(end_date)', 'YYYYMMDD')
        GROUP BY cs_user_agent_;
    RESULT -> Junction
    RESULT -> Junction_3
Junction
    -> Junction_2
Junction_3
    -> Junction_4
Note: c_ip
SQLCreator_7 [off]
    DATASET = $(PostgreSQL_CONNECTION)
    EXPOSED_ATTRIBUTE_LIST = count,c_ip
    FORMAT = POSTGRES
    OUTPUT_FEATURES = DATA_ONLY
    POSTGRES_CREATE_FEATURE_TABLES_FROM_DATA = Yes
    POSTGRES_NAMED_CONNECTION = $(PostgreSQL_CONNECTION)
    POSTGRES_QUERY_FEATURE_TYPES_FOR_MERGE_FILTERS = Yes
    POSTGRES_READ_TIME_WITH_TIMEZONE = Yes
    SQL_STATEMENT:
      FME_SQL_DELIMITER ;
       SELECT count(c_ip) AS count, c_ip
         FROM logs.iis
        WHERE   date >= to_date('$(Start_date)', 'YYYYMMDD') AND date < to_date('$(end_date)', 'YYYYMMDD')
        GROUP BY c_ip;
    RESULT -> iis_client_ip (writer XLSXW_1)
Note: går nog inte att använda
iis_client_ip (writer XLSXW_1) [off]
    attributes: count number(20), c_ip string(20)
Note: sc_status
SQLCreator_8 [off]
    DATASET = $(PostgreSQL_CONNECTION)
    EXPOSED_ATTRIBUTE_LIST = count,sc_status
    FORMAT = POSTGRES
    OUTPUT_FEATURES = DATA_ONLY
    POSTGRES_CREATE_FEATURE_TABLES_FROM_DATA = Yes
    POSTGRES_NAMED_CONNECTION = $(PostgreSQL_CONNECTION)
    POSTGRES_QUERY_FEATURE_TYPES_FOR_MERGE_FILTERS = Yes
    POSTGRES_READ_TIME_WITH_TIMEZONE = Yes
    SQL_STATEMENT:
      FME_SQL_DELIMITER ;
       SELECT count(sc_status) AS count, sc_status
         FROM logs.iis
        WHERE   date >= to_date('$(Start_date)', 'YYYYMMDD') AND date < to_date('$(end_date)', 'YYYYMMDD')
        GROUP BY sc_status;
Note: sc_substatus
SQLCreator_10 [off]
    DATASET = $(PostgreSQL_CONNECTION)
    EXPOSED_ATTRIBUTE_LIST = count,sc_substatus
    FORMAT = POSTGRES
    OUTPUT_FEATURES = DATA_ONLY
    POSTGRES_CREATE_FEATURE_TABLES_FROM_DATA = Yes
    POSTGRES_NAMED_CONNECTION = $(PostgreSQL_CONNECTION)
    POSTGRES_QUERY_FEATURE_TYPES_FOR_MERGE_FILTERS = Yes
    POSTGRES_READ_TIME_WITH_TIMEZONE = Yes
    SQL_STATEMENT:
      FME_SQL_DELIMITER ;
       SELECT count(sc_substatus) AS count, sc_substatus
         FROM logs.iis
        WHERE   date >= to_date('$(Start_date)', 'YYYYMMDD') AND date < to_date('$(end_date)', 'YYYYMMDD')
        GROUP BY sc_substatus;
Note: sc_win32_status
SQLCreator_9 [off]
    DATASET = $(PostgreSQL_CONNECTION)
    EXPOSED_ATTRIBUTE_LIST = count,sc_win32_status
    FORMAT = POSTGRES
    OUTPUT_FEATURES = DATA_ONLY
    POSTGRES_CREATE_FEATURE_TABLES_FROM_DATA = Yes
    POSTGRES_NAMED_CONNECTION = $(PostgreSQL_CONNECTION)
    POSTGRES_QUERY_FEATURE_TYPES_FOR_MERGE_FILTERS = Yes
    POSTGRES_READ_TIME_WITH_TIMEZONE = Yes
    SQL_STATEMENT:
      FME_SQL_DELIMITER ;
       SELECT count(sc_win32_status) AS count, sc_win32_status
         FROM logs.iis
        WHERE   date >= to_date('$(Start_date)', 'YYYYMMDD') AND date < to_date('$(end_date)', 'YYYYMMDD')
        GROUP BY sc_win32_status;

Bookmark: testing mobile-stationär typ av webläsare mm
Note: början till att ta ut mobila resp stationära klienter
TestFilter_2
    DEFAULT_VALUE = <UNFILTERED>
    PASSED_TEST_GROUP_OUTPUT = FIRST
    TEST_LIST = "BOOL_OP,OR,COMPOSITE_TEST,""""""1"""""",TEST_CLAUSE,CASE_INSENSITIVE_TEST @Value(cs_user_agent_) CONTAINS iPad",ipad,"BOOL_OP,OR,COMPOSITE_TEST,""""""1"""""",TEST_CLAUSE,CASE_INSENSITIVE_TEST @Value(cs_user_agent_) CONTAINS Windows",Windows,"BOOL_OP,OR,COMPOSITE_TEST,""""""1"""""",TEST_CLAUSE,CASE_INSENSITIVE_TEST @Value(cs_user_agent_) CONTAINS Linux",Linux,"BOOL_OP,OR,COMPOSITE_TEST,""""""1"""""",TEST_CLAUSE,CASE_INSENSITIVE_TEST @Value(cs_user_agent_) CONTAINS Sony",Sony,"BOOL_OP,OR,COMPOSITE_TEST,""""""1"""""",TEST_CLAUSE,CASE_INSENSITIVE_TEST @Value(cs_user_agent_) CONTAINS Iphone",Iphone,"BOOL_OP,OR,COMPOSITE_TEST,""""""1"""""",TEST_CLAUSE,CASE_INSENSITIVE_TEST @Value(cs_user_agent_) CONTAINS Nokia",Nokia,"BOOL_OP,OR,COMPOSITE_TEST,""""""1"""""",TEST_CLAUSE,CASE_INSENSITIVE_TEST @Value(cs_user_agent_) CONTAINS Macintosh",Macintosh,"BOOL_OP,OR,COMPOSITE_TEST,""""""1"""""",TEST_CLAUSE,CASE_INSENSITIVE_TEST @Value(cs_user_agent_) CONTAINS Android",Android,"BOOL_OP,OR,COMPOSITE_TEST,""""""1"""""",TEST_CLAUSE,CASE_INSENSITIVE_TEST @Value(cs_user_agent_) CONTAINS SunOS",SunOS,"BOOL_OP,OR,COMPOSITE_TEST,""""""1"""""",TEST_CLAUSE,CASE_INSENSITIVE_TEST @Value(cs_user_agent_) CONTAINS CrOS",CrOS,"BOOL_OP,OR,COMPOSITE_TEST,""""""1"""""",TEST_CLAUSE,CASE_INSENSITIVE_TEST @Value(cs_user_agent_) CONTAINS Gecko",Gecko,"BOOL_OP,OR,COMPOSITE_TEST,""""""1"""""",TEST_CLAUSE,CASE_INSENSITIVE_TEST @Value(cs_user_agent_) CONTAINS Mac_PowerPC",Mac_PowerPC
    Windows -> Tester_2
    Linux -> Tester_4
Tester_2
    BOOL_OP = OR
    TEST_CLAUSE = CASE_INSENSITIVE_TEST @Value(cs_user_agent_) CONTAINS mobile
    TEST_MODE = TEST
Tester_4
    BOOL_OP = OR
    TEST_CLAUSE = CASE_INSENSITIVE_TEST @Value(cs_user_agent_) CONTAINS mobile
    TEST_MODE = TEST
TestFilter
    DEFAULT_VALUE = <UNFILTERED>
    PASSED_TEST_GROUP_OUTPUT = FIRST
    TEST_LIST = "BOOL_OP,OR,COMPOSITE_TEST,""""""1"""""",TEST_CLAUSE,CASE_INSENSITIVE_TEST @Value(cs_user_agent_) CONTAINS Mozilla",mozilla,"BOOL_OP,OR,COMPOSITE_TEST,""""""1"""""",TEST_CLAUSE,CASE_INSENSITIVE_TEST @Value(cs_user_agent_) CONTAINS Opera",@Value(cs_user_agent_) CONTAINS Opera,"BOOL_OP,OR,COMPOSITE_TEST,""""""1"""""",TEST_CLAUSE,CASE_INSENSITIVE_TEST @Value(cs_user_agent_) CONTAINS Firefox",@Value(cs_user_agent_) CONTAINS Firefox,"BOOL_OP,OR,COMPOSITE_TEST,""""""1"""""",TEST_CLAUSE,CASE_INSENSITIVE_TEST @Value(cs_user_agent_) CONTAINS Safari",@Value(cs_user_agent_) CONTAINS Safari,"BOOL_OP,OR,COMPOSITE_TEST,""""""1"""""",TEST_CLAUSE,CASE_INSENSITIVE_TEST @Value(cs_user_agent_) CONTAINS Dalvik",@Value(cs_user_agent_) CONTAINS Dalvik,"BOOL_OP,OR,COMPOSITE_TEST,""""""1"""""",TEST_CLAUSE,CASE_INSENSITIVE_TEST @Value(cs_user_agent_) CONTAINS Nokia",@Value(cs_user_agent_) CONTAINS Nokia
    mozilla -> AttributeManager
    @Value(cs_user_agent_) CONTAINS Opera -> AttributeManager_2
    @Value(cs_user_agent_) CONTAINS Firefox -> AttributeManager
AttributeManager
    ATTR_TABLE = SET_TO agent (varchar(7)) = mozilla
    -> Aggregator
AttributeManager_2
    ATTR_TABLE = SET_TO agent (varchar(5)) = opera
    -> Aggregator
Aggregator
    ACCUM_ATTRS = None
    AGGREGATE_TYPE = Homogeneous Collection (If Possible)
    COUNT_ATTR = nn
    GROUP_BY = agent
    MODE = Geometry - Assemble One Level
    SEP = ,
    SUM = count
