FME workspace xml2postgres2.fmw

Parameters:
- SourceDataset_XML = X:\geoserver\geoserver_audit_20250110_149.log   # Source XML File(s)
- DestDataset_POSTGRES = postgres@ages-monitoring_uuc-srv390_5434   # Connection

Readers:
- XML_1: XML from $(SourceDataset_XML)

Writers:
- POSTGRES_1: POSTGRES to $(DestDataset_POSTGRES)

Request (reader XML_1)
    attributes: EndTime xml_char(24), Host xml_char(23), HttpMethod xml_char(4), LabelsProcessingTime xml_decimal(2,0), Operation xml_char(7), Path xml_char(18), QueryString xml_char(248), RemoteAddr xml_char(12), RemoteHost xml_char(12), RemoteUser xml_char(6), Request.id xml_decimal(4,0), Resources xml_char(26), ResourcesProcessingTime xml_decimal(2,0), ResponseLength xml_decimal(5,0), ResponseStatus xml_decimal(4,0), Service xml_char(4), StartTime xml_char(25), SubOperation xml_char(1), TotalTime xml_decimal(3,0), Version xml_char(6), xml_fragment xml_xml, xml_id xml_char(15), xml_matched_element xml_char(8), xml_parent_child_pos xml_char(1), xml_parent_id xml_char(1)
    -> geoserver (writer POSTGRES_1)
geoserver (writer POSTGRES_1)
    attributes: endtime timestamp, host text, httpmethod varchar(20), labelsprocessingtime int2, operation text, path text, querystring text, remoteaddr text, remotehost text, remoteuser text, request_id int8, resources text, resourcesprocessingtime int8, responselength int8, responsestatus int8, service text, starttime timestamp, suboperation text, totaltime int8, version varchar(6)
