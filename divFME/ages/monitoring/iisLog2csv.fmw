FME workspace iisLog2csv.fmw

Parameters:
- DestDataset_TEXTLINE = C:\ny_slask\iis\csv\u_ex241008.csv   # Destination Text File
- SourceDataset_TEXTLINE = C:\ny_slask\iis\u_ex241008.log   # Source Log-file

Readers:
- TEXTLINE_1: TEXTLINE from $(SourceDataset_TEXTLINE)

Writers:
- TEXTLINE_2: TEXTLINE to $(DestDataset_TEXTLINE)
- CSV2_1: CSV2 to C:\ny_slask\test_iislogg.csv

AttributeManager_3
    ATTR_TABLE = SET_TO text_line_data (buffer) = @ReplaceString(@Value(text_line_data)," ",",",caseSensitive=TRUE)
    -> Tester
Tester
    BOOL_OP = OR
    TEST_CLAUSE = CASE_INSENSITIVE_TEST @Value(text_line_data) BEGINS_WITH #
    TEST_MODE = TEST
    PASSED -> Tester_2
    FAILED -> AttributeManager_2
Tester_2
    BOOL_OP = OR
    TEST_CLAUSE = TEST @Value(text_line_data) = #Fields:,date,time,s-ip,cs-method,cs-uri-stem,cs-uri-query,s-port,cs-username,c-ip,cs(User-Agent),cs(Referer),sc-status,sc-substatus,sc-win32-status,time-taken
    TEST_MODE = TEST
    PASSED -> Aggregator
Aggregator
    ACCUM_ATTRS_NAME = Use Attributes From One Feature
    AGGREGATE_TYPE = Homogeneous Collection (If Possible)
    MODE = Geometry - Assemble One Level
    SEP = ,
    AGGREGATE -> AttributeManager
AttributeManager
    ATTR_TABLE = SET_TO text_line_data (buffer) = @Substring(@Value(text_line_data),9,@StringLength(@Value(text_line_data)))
    -> FeaturePrioritizer [OutputFirst]
AttributeManager_2
    ATTR_TABLE = RENAME_SET_VALUE text_line_data (buffer)
    -> FeaturePrioritizer [OutputLast]
FeaturePrioritizer
    USE_GROUP_PROCESSING = NO
    -> text_line (writer TEXTLINE_2)

Bookmark: Reader Feature Types
text_line (reader TEXTLINE_1)
    attributes: text_line_data buffer
    -> AttributeManager_3

Bookmark: Writer Feature Types
text_line (writer TEXTLINE_2)
    attributes: text_line_data buffer

FME custom transformer FeaturePrioritizer
FeaturePrioritizer
FeaturePrioritizer outputs features in a sorted order according to which Input Port they enter.  Features that enter the OutputFirst Port, will be output first, and features that enter the OutputLast Port will be output last.
This is useful for Transformers and Writers that need features to enter in a particular order.  For example, Writers/FeatureWriters that rely on a separate Schema Feature to be the first to enter prior to the main data features to prevent a writing error,  or Transformers that aggregates or merges groups of features and are set to only use one feature as the Attributes for the output etc.

Parameters:
- USE_GROUP_PROCESSING = NO   # Group Processing
- GROUPBY =   # "" Group By
- GROUP_BY_MODE = No   # Process At End (Blocking),No%Process When Group Changes (Advanced),Yes Group By Mode

OutputFirst (input)
    -> AttributeCreator
Note: Create an Order Attribute = 1st
AttributeCreator
    ATTR_TABLE = SET_TO _feat_prioritiser_order = @Evaluate(1)
    -> Sorter
OutputLast (input)
    -> AttributeCreator_2
Note: Create an Order Attribute = 2nd
AttributeCreator_2
    ATTR_TABLE = SET_TO _feat_prioritiser_order = @Evaluate(2)
    -> Sorter
Note: Sort the Features by Order Attribute
Sorter
    GROUP_BY = $(GROUPBY)
    SORT_PARM = _feat_prioritiser_order NUMERIC ASCENDING
    SORTED -> AttributeRemover
Note: Remove the temporary Order Attribute
AttributeRemover
    REMOVE_ATTRS = _feat_prioritiser_order
    -> Output (output)
Output (output)
