FME workspace 6_create_AGES_index.fmw

Parameters:
- SourceDataset_POSTGIS = ages-external   # Connection
- DestDataset_OGCGEOPACKAGE = C:\ny_slask\AGES_index.gpkg   # GeoPackage File
- SourceDataset_POSTGRES = uuc-srv390_ages_5434   # Connection
- SourceDataset_POSTGIS_3 = uuc-srv390_ages_5434   # Connection

Readers:
- POSTGIS_1: POSTGIS from $(SourceDataset_POSTGIS)
- POSTGRES_1: POSTGRES from $(SourceDataset_POSTGRES)
- POSTGIS_2: POSTGIS from $(SourceDataset_POSTGIS_3)

Writers:
- OGCGEOPACKAGE_1: OGCGEOPACKAGE to $(DestDataset_OGCGEOPACKAGE) in EPSG:3006

geodata_info (reader POSTGIS_1)
    attributes: geodatafil text, uppdragsnummer text, uppdragstyp text, diarienummer text, utforande_organisation text, beslutande_myndighet text, beslutsdatum text, kommun text, lan text, socken text, link_geodata text, link_fornsok text, forfattare varchar, titel varchar, utgivningsar varchar, link_rapport_info varchar
    -> project_information (writer OGCGEOPACKAGE_1)
    -> FeatureMerger_2 [SUPPLIER]
project_information (writer OGCGEOPACKAGE_1)
    attributes: geodatafil text, uppdragsnummer text, uppdragstyp text, diarienummer text, utforande_organisation text, beslutande_myndighet text, beslutsdatum text, kommun text, lan text, socken text, link_geodata text, link_fornsok text, forfattare text, titel text, utgivningsar text, link_rapport_info text

Bookmark: lite tester
geodata_info (reader POSTGIS_2)
    attributes: geopackage text, gpkg_uuid uuid,PrimaryKey, leverans text
    -> FeatureMerger [SUPPLIER]
rel2uppdrag (reader POSTGRES_1)
    attributes: gpkg_uuid uuid, uppdrag_uuid uuid
    -> FeatureMerger [REQUESTOR]
FeatureMerger
    ATTR_ACCUM_MODE = Merge Supplier
    ATTR_CONFLICT_RES_LOOKUP = REQUESTOR_IF_CONFLICT
    IGNORE_NULLS = No
    JOIN_KEYS = @Value(gpkg_uuid) @Value(gpkg_uuid) AUTO
    MERGE_TYPE_VAL = GEOM_AND_ATTRS
    PROCESS_DUPS = NO
    REJECT_NULL_MISSING_KEYS = No
    SUPPLIERS_FIRST = No
    ATTR_CONFLICT_RES = Use Requestor
    MERGE_TYPE = Attributes and Geometry
    MERGED -> DuplicateFilter
DuplicateFilter
    INPUT_ORDERED_CHOICE_LOOKUP = NO
    KEYATTR = uppdrag_uuid gpkg_uuid
    INPUT_ORDERED_CHOICE = No
    UNIQUE -> FeatureMerger_2 [REQUESTOR]
FeatureMerger_2
    ATTR_ACCUM_MODE = Merge Supplier
    ATTR_CONFLICT_RES_LOOKUP = REQUESTOR_IF_CONFLICT
    IGNORE_NULLS = No
    JOIN_KEYS = @Value(geopackage) @Value(geodatafil) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
