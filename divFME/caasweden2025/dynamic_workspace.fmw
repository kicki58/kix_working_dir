FME workspace dynamic_workspace.fmw

Parameters:
- SourceDataset_SHAPEFILE = ""C:\ny_slask\Dalarnas_museum\DM2021BRO1782_2022-06-21\Gisdata\lamning_inom_FU.shp" "C:\ny_slask\Dalarnas_museum\DM2021BRO1782_2022-06-21\Gisdata\Schakt östra.shp" "C:\ny_slask\Dalarnas_museum\DM2021BRO1782_2022-06-21\Gisdata\Västra_FU-området.shp" "C:\ny_slask\Dalarnas_museum\DM2021BRO1782_2022-06-21\Gisdata\Östra_FU-området.shp""   # Source Esri Shapefile(s)
- FEATURE_TYPES_2 = lamning_inom_FU Schakt östra Västra_FU-området Östra_FU-området
- DestDataset_OGCGEOPACKAGE_4 = C:\ny_slask\caa2025\test_dynamic.gpkg   # GeoPackage File

Readers:
- SHAPEFILE_1: SHAPEFILE from $(SourceDataset_SHAPEFILE)
- SCHEMA_1: SCHEMA from $(SourceDataset_SHAPEFILE)

Writers:
- OGCGEOPACKAGE_3: OGCGEOPACKAGE to $(DestDataset_OGCGEOPACKAGE_4)

lamning_inom_FU (reader SHAPEFILE_1)
    attributes: id varchar(80), lamningsnr varchar(11), raa_nr_old varchar(254), lamningtyp varchar(254), besk varchar(254), egenskap varchar(159), ing_lamn varchar(254), pub_av_org varchar(254), sen_andrad date, uttag_dat date, ant_bed varchar(254), ant_bed_mo varchar(254), ant_bed_kv varchar(113), aktstatus varchar(254), skadestat varchar(254), understat varchar(254), placering varchar(254), terrang varchar(254), orienter varchar(254), tradition varchar(254), inmat_kval varchar(80), inmat_medf varchar(80), Anl varchar(5), Area double, Id long, Name varchar(50)
    -> FeatureMerger [REQUESTOR]
schema (reader SCHEMA_1)
    attributes: fme_feature_type_name varchar(200)
    -> FeatureMerger [SUPPLIER]
FeatureMerger
    ATTR_ACCUM_MODE = Merge Supplier
    ATTR_CONFLICT_RES_LOOKUP = REQUESTOR_IF_CONFLICT
    IGNORE_NULLS = No
    JOIN_KEYS = @Value(fme_feature_type) @Value(fme_feature_type_name) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> Table100 (writer OGCGEOPACKAGE_3)
Table100 (writer OGCGEOPACKAGE_3)
