FME workspace filegdb2ogcgeopackage.fmw

Parameters:
- SourceDataset_FILEGDB = C:\ny_slask\samlingar_och_samband\Kalmar\Projekt\A1807 E4 Ljungby N\GISdata\A1807 Ljungby N.gdb   # File Geodatabase
- DestDataset_OGCGEOPACKAGE = C:\ny_slask\samlingar_och_samband\Kalmar\kix\first_try.gpkg   # GeoPackage File

Readers:
- FILEGDB_1: FILEGDB from $(SourceDataset_FILEGDB)

Writers:
- OGCGEOPACKAGE_1: OGCGEOPACKAGE to $(DestDataset_OGCGEOPACKAGE)

Referenspunkt__ATTACH (reader FILEGDB_1)
    attributes: ATTACHMENTID objectid, REL_OBJECTID int, CONTENT_TYPE text(150), ATT_NAME text(250), DATA_SIZE int, DATA blob
Linje__ATTACH (reader FILEGDB_1)
    attributes: ATTACHMENTID objectid, REL_OBJECTID int, CONTENT_TYPE text(150), ATT_NAME text(250), DATA_SIZE int, DATA blob
Referenspunkt (reader FILEGDB_1)
    attributes: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
Prov__ATTACH (reader FILEGDB_1)
    attributes: ATTACHMENTID objectid, REL_OBJECTID int, CONTENT_TYPE text(150), ATT_NAME text(250), DATA_SIZE int, DATA blob
Kontext__ATTACH (reader FILEGDB_1)
    attributes: ATTACHMENTID objectid, REL_OBJECTID int, CONTENT_TYPE text(150), ATT_NAME text(250), DATA_SIZE int, DATA blob
Fynd (reader FILEGDB_1)
    attributes: OBJECTID objectid, id int, fnr smallint, kxttyp smallint, utyp text(50), mk text(50), sk text(50), anr int, pid text(50), ar smallint, ai text(50), ap text(50), et text(50), sak text(50), land text(50), lan text(50), laskp text(50), kn text(50), sn text(50), ort_pnamn text(50), kv_ga text(50), fa text(50), ekkart text(50), koord text(50), moh smallint, muh smallint, ftyp text(50), raa text(50), und text(50), lst_dnr text(50),
      ref text(50), und_tid text(50), fotonr int, status text(50), fak text(50), koord_1 text(50), ant smallint, ld double, bd double, dp double, vikt double, mat_1 text(50), mat_2 text(50), sak_1 text(50), sak_2 text(50), del text(50), tek_1 text(50), dek text(50), deo_tek text(50), p_txt text(50), farg text(50), gt text(50), ma text(50), mag_max text(50), mag_and text(50), ytb text(50), brann text(50), anm text(2000), dat_met text(50), dat_year text(50),
      dat_a text(50), dat_b text(50), dat_c text(50), pro text(50), atyp text(50), atyp_prec text(50), rel int, schnr int, ruta int, lager int, dat date, sign text(50), art text(50), arti text(50), andel text(50), fus text(50), pat text(500), kl text(50), taf1 text(50), taf2 text(50), taf3 text(50), taf4 text(50), taf5 text(50), taf6 text(50), taf7 text(50), stat text(50), zt double, zb double, esrignss_receiver text(50), esrignss_h_rms double,
      esrignss_v_rms double, esrignss_latitude double, esrignss_longitude double, esrignss_altitude double, esrignss_fixtype smallint, esrignss_correctionage double, esrignss_stationid smallint, esrignss_numsats smallint, esrignss_fixdatetime date, brant text(50)
    -> AttributeRemover
AttributeRemover
    REMOVE_ATTRS = esrignss_altitude,esrignss_correctionage,esrignss_fixdatetime,esrignss_fixtype,esrignss_h_rms,esrignss_latitude,esrignss_longitude,esrignss_numsats,esrignss_receiver,esrignss_stationid,esrignss_v_rms
    -> Fynd (writer OGCGEOPACKAGE_1)
Fynd (writer OGCGEOPACKAGE_1)
    attributes: OBJECTID mediumint, id mediumint, fnr smallint, kxttyp smallint, utyp text(50), mk text(50), sk text(50), anr mediumint, pid text(50), ar smallint, ai text(50), ap text(50), et text(50), sak text(50), land text(50), lan text(50), laskp text(50), kn text(50), sn text(50), ort_pnamn text(50), kv_ga text(50), fa text(50), ekkart text(50), koord text(50), moh smallint, muh smallint, ftyp text(50), raa text(50), und text(50), lst_dnr text(50),
      ref text(50), und_tid text(50), fotonr mediumint, status text(50), fak text(50), koord_1 text(50), ant smallint, ld double, bd double, dp double, vikt double, mat_1 text(50), mat_2 text(50), sak_1 text(50), sak_2 text(50), del text(50), tek_1 text(50), dek text(50), deo_tek text(50), p_txt text(50), farg text(50), gt text(50), ma text(50), mag_max text(50), mag_and text(50), ytb text(50), brann text(50), anm text(2000), dat_met text(50), dat_year text(50),
      dat_a text(50), dat_b text(50), dat_c text(50), pro text(50), atyp text(50), atyp_prec text(50), rel mediumint, schnr mediumint, ruta mediumint, lager mediumint, dat datetime, sign text(50), art text(50), arti text(50), andel text(50), fus text(50), pat text(500), kl text(50), taf1 text(50), taf2 text(50), taf3 text(50), taf4 text(50), taf5 text(50), taf6 text(50), taf7 text(50), stat text(50), zt double, zb double, brant text(50)
Kontext (reader FILEGDB_1)
    attributes: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
Linje (reader FILEGDB_1)
    attributes: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
Prov (reader FILEGDB_1)
    attributes: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
Schakt (reader FILEGDB_1)
    attributes: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
Schakt__ATTACH (reader FILEGDB_1)
    attributes: ATTACHMENTID objectid, REL_OBJECTID int, CONTENT_TYPE text(150), ATT_NAME text(250), DATA_SIZE int, DATA blob
Fynd__ATTACH (reader FILEGDB_1)
    attributes: ATTACHMENTID objectid, REL_OBJECTID int, CONTENT_TYPE text(150), ATT_NAME text(250), DATA_SIZE int, DATA blob
