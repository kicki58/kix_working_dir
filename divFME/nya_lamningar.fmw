FME workspace nya_lamningar.fmw

Parameters:
- SourceDataset_OGCGEOPACKAGE = C:\Users\krima354\Downloads\POC_lamningar_sverige_a_pub_v11.gpkg   # GeoPackage File
- SourceDataset_SQLITE3_2 = C:\Users\krima354\Downloads\POC_lamningar_sverige_a_pub_v11.gpkg   # SQLite Database
- SourceDataset_SQLITE3 = C:\Users\krima354\Downloads\sau20101ras634.gpkg   # SQLite Database
- DestDataset_SQLITE3 = C:\Users\krima354\Downloads\POC_lamningar_sverige_a_pub_v11.gpkg   # SQLite Database
- DestDataset_OGCGEOPACKAGE = C:\Users\krima354\Downloads\POC_lamningar_sverige_a_pub_v11.gpkg   # GeoPackage File

Readers:
- OGCGEOPACKAGE_1: OGCGEOPACKAGE from $(SourceDataset_OGCGEOPACKAGE)
- SQLITE3_3: SQLITE3 from $(SourceDataset_SQLITE3)
- SQLITE3_4: SQLITE3 from $(SourceDataset_SQLITE3_2)

Writers:
- OGCGEOPACKAGE_2: OGCGEOPACKAGE to $(DestDataset_OGCGEOPACKAGE)
- SQLITE3_1: SQLITE3 to $(DestDataset_SQLITE3)

ingaendelamning (reader OGCGEOPACKAGE_1)
    attributes: id int, lamning_uuid text, antal mediumint, lamningstyp text(255), fid int,PrimaryKey
    -> AttributeKeeper
AttributeKeeper
    CREATE_BULK_MODE_FEATURES = NO
    KEEP_ATTRS = id,lamning_uuid
    -> BulkAttributeRenamer
BulkAttributeRenamer
    ATTRCHOICE_ACTION = NONPROTECTEDFME
    MODE_CHOICE = RENAME
    PATTERN_ACTION_DISP = ADDSUFFIX
    REPLACE_STR = _ingaende
    ATTRCHOICE = All Attributes
    -> FeatureMerger [SUPPLIER]
lamning (reader OGCGEOPACKAGE_1)
    attributes: uuid text, lamningsnummer text(11), raa_nummer text(300), lamningstyp text(255), antikvariskbedomning text(255), antikvariskbedomning_motivering text, beskrivning text, aktualitetstatus text(255), skadestatus text(255), undersokningsstatus text(255), placering text(255), terrang text, orientering text, tradition text, lamningsnamn text(300), publicerad_av text(255), publiceringsdatum datetime, inspire_ruin boolean, url text, lan text, kommun text, socken text, uttagsdatum date, fid int,PrimaryKey
    -> AttributeKeeper_2
AttributeKeeper_2
    CREATE_BULK_MODE_FEATURES = NO
    KEEP_ATTRS = uuid,fid
    -> FeatureMerger [REQUESTOR]
FeatureMerger
    ATTR_ACCUM_MODE = Merge Supplier
    ATTR_CONFLICT_RES_LOOKUP = REQUESTOR_IF_CONFLICT
    CLEANING_TOLERANCE_LOOKUP = AUTO
    CONNECT_Z_MODE_LOOKUP = FIRST_WINS
    GEOM_TYPE_VAL = POLYGONS
    IGNORE_NULLS = No
    JOIN_KEYS = @Value(uuid) @Value(lamning_uuid_ingaende) AUTO
    LIST_ATTRS_TO_INCLUDE = id_ingaende lamning_uuid_ingaende
    LIST_NAME = _list
    MERGE_TYPE_VAL = ATTRIBUTES
    PROCESS_DUPS = YES
    REJECT_NULL_MISSING_KEYS = No
    SUPPLIERS_FIRST = No
    ATTR_CONFLICT_RES = Use Requestor
    CLEANING_TOLERANCE = Automatic
    CONNECT_Z_MODE = First Wins
    GEOM_TYPE = Build Polygons
    MERGE_TYPE = Attributes Only
    MERGED -> ListExploder
ListExploder
    ATTR_CONFLICT_RES_LOOKUP = INCOMING_IF_CONFLICT
    INDEX_ATTR = _element_index
    LIST_ATTR = _list{}
    ATTR_ACCUM_MODE = Merge List Attributes
    ATTR_CONFLICT_RES = Use List Attribute Values
    ELEMENTS -> Counter
Counter
    CNT_ATTR = id
    SCOPE = Local
    START = 0
    -> AttributeManager
AttributeManager
    ATTR_TABLE:
      RENAME_SET_VALUE fid > base_id (int64)
      RENAME_SET_VALUE id_ingaende > related_id (int64)
      REMOVE uuid (buffer)
      REMOVE lamning_uuid_ingaende (buffer)
    USER_EXPOSED_ATTRIBUTES = id,lamning_uuid,_count
    -> ingaende_relations (writer OGCGEOPACKAGE_2)
ingaende_relations (writer OGCGEOPACKAGE_2)
    attributes: id int, related_id int, base_id int
gpkg_extensions (reader SQLITE3_3)
    attributes: table_name text,Unique, column_name text,Unique, extension_name text,Unique, definition text, scope text
    -> Tester
Tester
    BOOL_OP = AND
    TEST_CLAUSE:
      TEST @Value(extension_name) = related_tables
      TEST @Value(table_name) = gpkgext_relations
    TEST_MODE = TEST
    PASSED -> gpkg_extensions (writer SQLITE3_1)
gpkgext_relations (reader SQLITE3_3)
    attributes: id integer, base_table_name text, base_primary_column text, related_table_name text, related_primary_column text, relation_name text, mapping_table_name text,Unique
    -> AttributeFilter
AttributeFilter
    ATTR_NAME = id
    ATTR_VALUES = <Empty>,<Missing>,<Null>,<Unfiltered>,1
    <UNFILTERED> -> AttributeManager_2
AttributeManager_2
    ATTR_TABLE:
      SET_TO id (int64) = 1
      SET_TO base_table_name (buffer) = lamning
      SET_TO base_primary_column (buffer) = fid
      SET_TO related_table_name (buffer) = ingaendelamning
      SET_TO related_primary_column (buffer) = fid
      SET_TO relation_name (buffer) = ing_rel
      SET_TO mapping_table_name (buffer) = ingaende_relations
    -> gpkgext_relations (writer SQLITE3_1)
gpkgext_relations (writer SQLITE3_1)
    attributes: id integer, base_table_name text, base_primary_column text, related_table_name text, related_primary_column text, relation_name text, mapping_table_name text,Unique
gpkg_extensions (reader SQLITE3_4)
    attributes: table_name text,Unique, column_name text,Unique, extension_name text,Unique, definition text, scope text
Creator
    GEOMTYPE = Geometry Object
    NUM = 1
    CREATED -> AttributeManager_3
AttributeManager_3
    ATTR_TABLE:
      REMOVE _creation_instance (uint64)
      SET_TO table_name (varchar(17)) = ingaede_relations
      SET_TO column_name (varchar(200))
      SET_TO extension_name (varchar(14)) = related_tables
      SET_TO definition (varchar(37)) = http://www.geopackage.org/18-000.html
      SET_TO scope (varchar(10)) = read-write
    -> gpkg_extensions (writer SQLITE3_1)
gpkg_extensions (writer SQLITE3_1)
    attributes: table_name text,Unique, column_name text,Unique, extension_name text,Unique, definition text, scope text
attribute_relations (reader SQLITE3_3) [off]
    attributes: id integer, related_id integer, base_id integer
    -> attribute_relations (writer SQLITE3_1) [off]
attribute_relations (writer SQLITE3_1) [off]
    attributes: id integer, related_id integer, base_id integer
Table1 (writer OGCGEOPACKAGE_2) [off]

Bookmark: New Bookmark
lamningar_sverige_linestring (reader OGCGEOPACKAGE_1)
    attributes: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
lamningar_sverige_point (reader OGCGEOPACKAGE_1)
    attributes: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
lamningar_sverige_polygon (reader OGCGEOPACKAGE_1)
    attributes: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
egenskap (reader OGCGEOPACKAGE_1)
    attributes: id int, lamning_uuid text, ingaendelamning_id int, typ text(255), varde text(255), fid int,PrimaryKey
lagesosakerhet (reader OGCGEOPACKAGE_1)
    attributes: lamning_uuid text, lamningsnummer text(11), inmatningskvalitet text(255), definition_av_kvalitet text, lagesosakerhet mediumint, url text, fid int,PrimaryKey
linestring (reader OGCGEOPACKAGE_1)
    attributes: lamning_uuid text, geometrinummer mediumint, fid int,PrimaryKey
point (reader OGCGEOPACKAGE_1)
    attributes: lamning_uuid text, geometrinummer mediumint, fid int,PrimaryKey
polygon (reader OGCGEOPACKAGE_1)
    attributes: lamning_uuid text, geometrinummer mediumint, fid int,PrimaryKey

Bookmark: ages-tables
gpkg_contents (reader SQLITE3_3)
    attributes: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
