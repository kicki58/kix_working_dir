FME workspace sau_reproject.fmw

Parameters:
- SourceDataset_CSV2 = $(FME_MF_DIR)sau_alla.csv   # Source CSV (Comma Separated Value) File(s)
- HOST_POSTGISserver = uuc-srv390.user.uu.se   # Server
- USER_NAME_POSTGIS_2 = postgres   # Username
- PASSWORD_2 =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   # Password
- PORT_POSTGIS_2 = 5432   # Port

Readers:
- CSV2_1: CSV2 from $(SourceDataset_CSV2)

CSV (reader CSV2_1)
    attributes: Databas varchar(27), SRID varchar(10), SRID_org uint32, anteckning varchar(48), ändrat attributet i DB varchar(2)
    -> TestFilter
TestFilter
    DEFAULT_VALUE = <UNFILTERED>
    PASSED_TEST_GROUP_OUTPUT = FIRST
    TEST_LIST:
      "BOOL_OP,OR,COMPOSITE_TEST,""""""1"""""",TEST_CLAUSE,TEST @Value(SRID) = 3009",@Value(SRID) = 3009,"BOOL_OP,OR,COMPOSITE_TEST,""""""1"""""",TEST_CLAUSE,TEST @Value(SRID) = 3021",@Value(SRID) = 3021,"BOOL_OP,OR,COMPOSITE_TEST,""""""1"""""",TEST_CLAUSE,TEST @Value(SRID) = 3022",@Value(SRID) = 3022,"BOOL_OP,OR,COMPOSITE_TEST,""""""1"""""",TEST_CLAUSE,TEST @Value(SRID) = 3027",@Value(SRID) = 3027,"BOOL_OP,OR,COMPOSITE_TEST,""""""1"""""",TEST_CLAUSE,TEST @Value(SRID) = 3027",@Value(SRID) = 3027,"BOOL_OP,OR,COMPOSITE_TEST,""""""1 OR 2"""""",TEST_CLAUSE,TEST @Value(SRID) = st74_65-1
      TEST @Value(SRID) = st74-65-1",@Value(SRID) = st74_65-1,"BOOL_OP,OR,COMPOSITE_TEST,""""""1"""""",TEST_CLAUSE,TEST @Value(SRID) = UK72",@Value(SRID) = UK72,"BOOL_OP,OR,COMPOSITE_TEST,""""""1"""""",TEST_CLAUSE,TEST @Value(SRID) = 3006",@Value(SRID) = 3006
    @Value(SRID) = 3009 -> AttributeManager
    @Value(SRID) = 3021 -> AttributeManager
    @Value(SRID) = 3022 -> AttributeManager
    @Value(SRID) = 3027 -> AttributeManager
    @Value(SRID) = st74_65-1 -> WorkspaceRunner_2
    @Value(SRID) = UK72 -> WorkspaceRunner_3
AttributeManager
    ATTR_TABLE = SET_TO srid_epsg = EPSG:@Value(SRID)
    -> WorkspaceRunner
WorkspaceRunner
    BLOCKING = Yes
    WORKSPACE_FILE = $(FME_MF_DIR)sau_reproject_epsg.fmw
    WORKSPACE_PARAMETERS = HOST_POSTGISserver,$(HOST_POSTGISserver),Source_Dest_Dataset_POSTGIS_2,@Value(Databas),USER_NAME_POSTGIS_2,$(USER_NAME_POSTGIS_2),PASSWORD_2,$(PASSWORD_2),PORT_POSTGIS_2,$(PORT_POSTGIS_2),SOURCE,@Value(srid_epsg)
WorkspaceRunner_2
    BLOCKING = Yes
    WORKSPACE_FILE = $(FME_MF_DIR)sau_reproject_st74.fmw
    WORKSPACE_PARAMETERS = HOST_POSTGISserver,$(HOST_POSTGISserver),Source_Dest_Dataset_POSTGIS_2,@Value(Databas),USER_NAME_POSTGIS_2,$(USER_NAME_POSTGIS_2),PASSWORD_2,$(PASSWORD_2),PORT_POSTGIS_2,$(PORT_POSTGIS_2)
WorkspaceRunner_3
    BLOCKING = Yes
    WORKSPACE_FILE = $(FME_MF_DIR)sau_reproject_UK72.fmw
    WORKSPACE_PARAMETERS = HOST_POSTGISserver,$(HOST_POSTGISserver),Source_Dest_Dataset_POSTGIS_2,@Value(Databas),USER_NAME_POSTGIS_2,$(USER_NAME_POSTGIS_2),PASSWORD_2,$(PASSWORD_2),PORT_POSTGIS_2,$(PORT_POSTGIS_2)
