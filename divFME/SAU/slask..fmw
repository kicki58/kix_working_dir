FME workspace slask..fmw

Parameters:
- SourceDataset_OGCGEOPACKAGE = C:\Users\krima354\Work Folders\Documents\kicki_arbetsfiler\slask\sau_all_bb16.gpkg   # GeoPackage File

Readers:
- OGCGEOPACKAGE_1: OGCGEOPACKAGE from $(SourceDataset_OGCGEOPACKAGE) in EPSG:3006
- CSV2_1: CSV2 from $(FME_MF_DIR)sau_alla.csv

CSV (reader CSV2_1)
    attributes: Databas varchar(27), SRID varchar(10), SRID_org uint32, anteckning varchar(48), ändrat attributet i DB varchar(2)
    -> AttributeManager
AttributeManager
    ATTR_TABLE = SET_TO Databas = @LowerCase(@Value(Databas))
    -> FeatureMerger [REQUESTOR]
intrasis_bb (reader OGCGEOPACKAGE_1)
    attributes: from_intrasis_Projektnamn text(200), from_intrasis_Exploateringstyp text(200), from_intrasis_Inventarienummer text(200), from_intrasis_Lst Dnr text(200), from_intrasis_Plats text(200), from_intrasis_Projektkod text(200), from_intrasis_Projektledare text(200), from_intrasis_Raä Dnr text(200), from_intrasis_Slutdatum text(200), from_intrasis_Undersöknings Id text(200), from_intrasis_Undersökningstyp text(200), from_intrasis_Uppdragsgivare text(200), databas text(200), fme_rejection_code text, id int,PrimaryKey
    -> AttributeManager_2
AttributeManager_2
    ATTR_TABLE = SET_TO from_intrasis_Undersöknings Id = @LowerCase(@Value(from_intrasis_Undersöknings Id))
    -> FeatureMerger [SUPPLIER]
FeatureMerger
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = @Value(Databas) @Value(databas) AUTO
    LIST_ATTRS_TO_INCLUDE = databas
    LIST_NAME = list
    MERGE_TYPE = Attributes Only
    PROCESS_DUPS = YES
    REJECT_NULL_MISSING_KEYS = No
    SUPPLIERS_FIRST = No
