FME workspace resore_firsttry.fmw

Parameters:
- SourceDataset_PATH = C:\Program Files\Microsoft SQL Server\MSSQL13.SQLEXPRESS\MSSQL\Backup\MM_Backup_DB   # INCLUDE_WEB_BROWSER Source Folder and File Pathnames Folder
- mssqlfolder = C:\Program Files\Microsoft SQL Server\MSSQL13.SQLEXPRESS\MSSQL
- host = UUC-SRV390\SQLEXPRESS   # MSSQL host
- num2remove = 33

Readers:
- PATH_1: PATH from $(SourceDataset_PATH)

PATH (reader PATH_1)
    attributes: path_unix buffer, path_windows buffer, path_rootname buffer, path_filename buffer, path_extension buffer, path_directory_unix buffer, path_directory_windows buffer, path_type char(10)
    -> TestFilter
TestFilter
    DEFAULT_VALUE = <UNFILTERED>
    PASSED_TEST_GROUP_OUTPUT = FIRST
    TEST_LIST = "BOOL_OP,OR,COMPOSITE_TEST,""""""1"""""",TEST_CLAUSE,TEST @Value(path_rootname) = Fosiebyforskdata",@Value(path_rootname) = Fosiebyforskdata
    @Value(path_rootname) = Fosiebyforskdata -> SystemCaller
    <UNFILTERED> -> AttributeManager
AttributeManager
    ATTR_TABLE = SET_TO path_rootname = @Left(@Value(path_rootname),@StringLength(@Value(path_rootname))-$(num2remove))
    -> SystemCaller
SystemCaller
    CMD = sqlcmd -U intrasis -P sisartni58 -S $(host) -H $(host) -Q "RESTORE DATABASE @Value(path_rootname) FROM DISK='@Value(path_windows)'  WITH MOVE '@Value(path_rootname)' to '$(mssqlfolder)\DATA\@Value(path_rootname).mdf', MOVE '@Value(path_rootname)_log' to '$(mssqlfolder)\DATA\@Value(path_rootname).LDF';"
