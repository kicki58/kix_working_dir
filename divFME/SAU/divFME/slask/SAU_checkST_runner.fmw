FME workspace SAU_checkST_runner.fmw

Parameters:
- SourceDataset_XLSXR = C:\Users\krima354\Work Folders\Documents\kicki_arbetsfiler\slask\tillsholm.xlsx   # Source Microsoft Excel File(s)
- DestDataset_OGCGEOPACKAGE = C:\Users\krima354\Work Folders\Documents\kicki_arbetsfiler\slask\checkST.gpkg   # GeoPackage File

Readers:
- XLSXR_1: XLSXR from $(SourceDataset_XLSXR)

Writers:
- OGCGEOPACKAGE_1: OGCGEOPACKAGE to $(DestDataset_OGCGEOPACKAGE)

SAU (reader XLSXR_1)
    attributes: Databas char(27), SRID number(5,0)
    -> WorkspaceRunner
WorkspaceRunner
    BLOCKING = No
    MAX_TO_BATCH = 1
    WORKSPACE_FILE = $(FME_MF_DIR)SAU_checkST.fmw
    WORKSPACE_PARAMETERS = SourceDataset_POSTGIS_2,@Value(Databas),USER_NAME_POSTGIS,postgres,PASSWORD,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,DestDataset_OGCGEOPACKAGE,$(DestDataset_OGCGEOPACKAGE)
