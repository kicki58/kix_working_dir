FME workspace jmrShape_fixedGeom_med_urdar.fmw

Parameters:
- GEOPACKAGE = C:\Users\krima354\Work Folders\Documents\kicki_arbetsfiler\urdar_arbetsfiler\create_siteinfo\Fixed geometries\Fixed geometries\NEW Sept 2021\uv2012193.gpkg   # gpkg file
- SourceDataset_POSTGIS_2 = uv2012193   # Database
- USER_NAME_POSTGIS = kicki   # Username
- PASSWORD =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   # Password
- SourceDataset_SHAPEFILE_5 = C:\Users\krima354\Work Folders\Documents\kicki_arbetsfiler\urdar_arbetsfiler\create_siteinfo\Fixed geometries\Fixed geometries\b20024\geo_objs_all_line.shp   # ShapefileLine
- SourceDataset_SHAPEFILE_4 = C:\Users\krima354\Work Folders\Documents\kicki_arbetsfiler\urdar_arbetsfiler\create_siteinfo\Fixed geometries\Fixed geometries\uv2010096\geo_objs_all_points.shp   # ShapefilePoint
- SourceDataset_SHAPEFILE = C:\Users\krima354\Work Folders\Documents\kicki_arbetsfiler\urdar_arbetsfiler\create_siteinfo\Fixed geometries\Fixed geometries\b20024\geo_objs_all.shp   # Shapefile_poly

Readers:
- SHAPEFILE_1: SHAPEFILE from $(SourceDataset_SHAPEFILE)
- POSTGIS_1: POSTGIS from $(SourceDataset_POSTGIS_2) in EPSG:3006
- SHAPEFILE_2: SHAPEFILE from $(SourceDataset_SHAPEFILE_5)
- SHAPEFILE_3: SHAPEFILE from $(SourceDataset_SHAPEFILE_4)

Writers:
- OGCGEOPACKAGE_1: OGCGEOPACKAGE to $(GEOPACKAGE)

geo_objs_all_points (reader SHAPEFILE_3)
    attributes: fid_1 number(20,0), intrasis_a varchar(254), object_ids varchar(254), occurrence varchar(254), pk long
    -> shapefile (writer OGCGEOPACKAGE_1)
    -> BoundingBoxAccumulator_2
geo_objs_all_line (reader SHAPEFILE_2)
    attributes: fid number(20,0), intrasis_a varchar(254), object_ids varchar(254), occurrence varchar(254), pk number(11,0)
    -> BoundingBoxAccumulator
    -> shapefile (writer OGCGEOPACKAGE_1)
geo_objs_all (reader SHAPEFILE_1)
    attributes: fid number(20,0), intrasis_a varchar(254), object_ids varchar(254), occurrence varchar(254), pk number(11,0)
    -> shapefile (writer OGCGEOPACKAGE_1)
    -> BoundingBoxAccumulator
BoundingBoxAccumulator
    ACCUM_ATTRS_NAME = Use Attributes From One Feature
    BOUNDING_BOX -> AttributeManager_2
AttributeManager_2
    ATTR_TABLE:
      SET_TO sitearchive = $(SourceDataset_POSTGIS_2)
      SET_TO from = shape
      REMOVE fid
      REMOVE intrasis_a
      REMOVE object_ids
      REMOVE occurrence
      REMOVE pk
    -> bounding_box (writer OGCGEOPACKAGE_1)
shapefile (writer OGCGEOPACKAGE_1)
    attributes: fid double, intrasis_a text(254), object_ids text(254), occurrence text(254), pk int, fid_1 double
GeoObject (reader POSTGIS_1)
    attributes: ObjectId int4, MetaId int4, SymbolId int4, the_raster raster
    -> BoundingBoxAccumulator_2
    -> AttributeManager_3
BoundingBoxAccumulator_2
    ACCUM_ATTRS_NAME = Use Attributes From One Feature
    BOUNDING_BOX -> AttributeManager
AttributeManager
    ATTR_TABLE:
      REMOVE ObjectId
      REMOVE MetaId
      REMOVE SymbolId
      REMOVE the_raster
      SET_TO sitearchive = $(SourceDataset_POSTGIS_2)
      SET_TO from = urdar
    -> bounding_box (writer OGCGEOPACKAGE_1)
bounding_box (writer OGCGEOPACKAGE_1)
    attributes: sitearchive text(200), from text(200), fid_1 double, intrasis_a text(254), object_ids text(254), occurrence text(254), pk mediumint
AttributeManager_3
    ATTR_TABLE = SET_TO intrasis_a = $(SourceDataset_POSTGIS_2)
    -> urdar (writer OGCGEOPACKAGE_1)
urdar (writer OGCGEOPACKAGE_1)
    attributes: ObjectId mediumint, MetaId mediumint, SymbolId mediumint, the_raster text(200), intrasis_a text(200)
