FME workspace jmfrZvarden3lists.fmw

Parameters:
- SourceDataset_POSTGIS_3 = o2007133   # Database
- DestDataset_OGCGEOPACKAGE = C:\Users\krima354\Work Folders\Documents\kicki_arbetsfiler\slask\urdat_geom_fix_Z\jmfrZ\jmfrZforResst__.gpkg   # GeoPackage File

Readers:
- POSTGIS_1: POSTGIS from $(SourceDataset_POSTGIS_3)
- POSTGIS_2: POSTGIS from $(SourceDataset_POSTGIS_3)

Writers:
- OGCGEOPACKAGE_1: OGCGEOPACKAGE to $(DestDataset_OGCGEOPACKAGE) in EPSG:3006

Note: uuc-srv
GeoObject (reader POSTGIS_2)
    attributes: ObjectId int4, MetaId int4, SymbolId int4, the_raster raster
    -> CoordinateExtractor_2
CoordinateExtractor_2
    LIST_NAME = _indices
    MODE = All Coordinates
    -> BulkAttributeRenamer_2
BulkAttributeRenamer_2
    ATTRCHOICE = All Attributes
    MODE_CHOICE = RENAME
    PATTERN_ACTION_DISP = ADDPREFIX
    REPLACE_STR = uuc-srv_
    -> FeatureMerger [REQUESTOR]
Note: localhost
GeoObject (reader POSTGIS_1)
    attributes: ObjectId int4, MetaId int4, SymbolId int4, the_raster raster
    -> CoordinateExtractor_3
CoordinateExtractor_3
    LIST_NAME = _indices
    MODE = All Coordinates
    -> BulkAttributeRenamer_3
BulkAttributeRenamer_3
    ATTRCHOICE = All Attributes
    MODE_CHOICE = RENAME
    PATTERN_ACTION_DISP = ADDPREFIX
    REPLACE_STR = localhost_
    -> FeatureMerger [SUPPLIER]
FeatureMerger
    ATTR_ACCUM_MODE = Merge Supplier
    ATTR_CONFLICT_RES = Use Requestor
    IGNORE_NULLS = No
    JOIN_KEYS = @Value(uuc-srv_ObjectId) @Value(localhost_ObjectId) AUTO
    MERGE_TYPE = Attributes Only
    PROCESS_DUPS = NO
    REJECT_NULL_MISSING_KEYS = No
    SUPPLIERS_FIRST = No
    MERGED -> ListElementCounter
ListElementCounter
    CNT_ATTR = _localhost_element_count
    LIST_NAME = localhost__indices{}
    -> ListElementCounter_2
ListElementCounter_2
    CNT_ATTR = _uuc-srv_element_count
    LIST_NAME = uuc-srv__indices{}
    -> ListConcatenator
ListConcatenator
    DROP_EMPTY_PARTS = No
    LIST_ATTR = localhost__indices{}.z
    SEP = ,
    VAL_ATTR = _concatenated_lh
    -> ListConcatenator_2
ListConcatenator_2
    DROP_EMPTY_PARTS = No
    LIST_ATTR = uuc-srv__indices{}.z
    SEP = ,
    VAL_ATTR = _concatenated_uuc
    -> GeometryExtractor
GeometryExtractor
    ATTR = _geometry
    KIND_LONG = OGC Well Known Text
    OGCVERSION = 1.2
    OGC_WKT_PRECISION_DISPLAY = 64-bit
    REMOVE_GEOMETRY = No
    -> Tester
Tester
    BOOL_OP = OR
    TEST_CLAUSE = TEST _concatenated_uuc ATTRIBUTE_HAS_A_VALUE ""
    TEST_MODE = TEST
    PASSED -> TestFilter_2
    FAILED -> Aggregator
TestFilter_2
    DEFAULT_VALUE = <UNFILTERED>
    PASSED_TEST_GROUP_OUTPUT = FIRST
    TEST_LIST = "BOOL_OP,OR,COMPOSITE_TEST,""""""1"""""",TEST_CLAUSE,TEST @Value(_concatenated_lh) = @Value(_concatenated_uuc)",@Value(_concatenated_lh) = @Value(_concatenated_uuc),"BOOL_OP,OR,COMPOSITE_TEST,""""""1"""""",TEST_CLAUSE,TEST @Value(_localhost_element_count) = @Value(_uuc-srv_element_count)",@Value(_localhost_element_count) = @Value(_uuc-srv_element_count)
    @Value(_concatenated_lh) = @Value(_concatenated_uuc) -> Aggregator_4
    @Value(_localhost_element_count) = @Value(_uuc-srv_element_count) -> PythonCaller
    <UNFILTERED> -> AttributeManager_4
    <UNFILTERED> -> Aggregator_2
AttributeManager_4
    ATTR_TABLE = SET_TO intrasisarchive = $(SourceDataset_POSTGIS_3)
    -> olika_antal_Z_varde (writer OGCGEOPACKAGE_1)
olika_antal_Z_varde (writer OGCGEOPACKAGE_1)
    attributes: intrasisarchive text(200), uuc-srv_ObjectId mediumint, uuc-srv_MetaId mediumint, uuc-srv_SymbolId mediumint, uuc-srv_the_raster text(200), uuc-srv__indices{}.x double, uuc-srv__indices{}.y double, uuc-srv__indices{}.z double, localhost_ObjectId mediumint, localhost_MetaId mediumint, localhost_SymbolId mediumint, localhost_the_raster text(200), localhost__indices{}.x double, localhost__indices{}.y double, localhost__indices{}.z double, _localhost_element_count text(20), _uuc-srv_element_count text(20), _concatenated_lh text, _concatenated_uuc text, _geometry text
Aggregator_2
    ACCUM_ATTRS_NAME = Drop Incoming Attributes
    AGGREGATE_TYPE = Homogeneous Collection (If Possible)
    COUNT_ATTR = _num
    MODE = Geometry - Assemble One Level
    SEP = ,
    AGGREGATE -> AttributeManager_3
AttributeManager_3
    ATTR_TABLE:
      SET_TO intrasisarchive = $(SourceDataset_POSTGIS_3)
      RENAME_SET_VALUE _num > object_med_olika_antal_z_varden
    -> FeatureMerger_4 [SUPPLIER]
PythonCaller
    NEW_ATTRIBUTES = antal_fel felmed
    PYTHONSOURCE:
      import fme
      import fmeobjects


      class FeatureProcessor(object):
          """Template Class Interface:
          When using this class, make sure its name is set as the value of the 'Class
          to Process Features' transformer parameter.
          """

          def __init__(self):
              """Base constructor for class members."""
              pass

          def input(self, feature):
              """This method is called for each FME Feature entering the
              PythonCaller. If knowledge of all input Features is not required for
              processing, then the processed Feature can be emitted from this method
              through self.pyoutput(). Otherwise, the input FME Feature should be
              cached to a list class member and processed in process_group() when
              'Group by' attributes(s) are specified, or the close() method.

              :param fmeobjects.FMEFeature feature: FME Feature entering the
                  transformer.
              """
              list_lh = feature.getAttribute('localhost__indices{}.z')
              list_uuc= feature.getAttribute('uuc-srv__indices{}.z')
              i=0
              antal_fel = 0
              fel= ''

              for item in list_lh:
                  if list_lh[i] != list_uuc[i]:
                      fel+= 'index: '+  f"{i}"+ ' ' +  f"{list_lh[i]}" + '!=' + f"{list_uuc[i]}"
                      antal_fel +=1
                  i+=1

              #feature.setAttribute('_geometry', geom_string)
              feature.setAttribute('antal_fel', antal_fel)
              feature.setAttribute('felmed', fel)
              self.pyoutput(feature)

          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> TestFilter_3
TestFilter_3
    DEFAULT_VALUE = <UNFILTERED>
    PASSED_TEST_GROUP_OUTPUT = FIRST
    TEST_LIST = "BOOL_OP,OR,COMPOSITE_TEST,""""""1"""""",TEST_CLAUSE,TEST antal_fel NOT_ATTRIBUTE_HAS_A_VALUE """,antal_fel NOT_ATTRIBUTE_HAS_A_VALUE,"BOOL_OP,OR,COMPOSITE_TEST,""""""1"""""",TEST_CLAUSE,TEST @Value(antal_fel) >= 1",@Value(antal_fel) >=1
    antal_fel NOT_ATTRIBUTE_HAS_A_VALUE -> samma_Z_varde (writer OGCGEOPACKAGE_1)
    antal_fel NOT_ATTRIBUTE_HAS_A_VALUE -> Aggregator_4
    @Value(antal_fel) >=1 -> AttributeManager
    @Value(antal_fel) >=1 -> Aggregator_3
    <UNFILTERED> -> AttributeManager_7
AttributeManager
    ATTR_TABLE = SET_TO intrasisarchive = $(DestDataset_OGCGEOPACKAGE)
    -> olika_Z_varde (writer OGCGEOPACKAGE_1)
olika_Z_varde (writer OGCGEOPACKAGE_1)
    attributes: intrasisarchive text(200), uuc-srv_ObjectId mediumint, uuc-srv_MetaId mediumint, uuc-srv_SymbolId mediumint, uuc-srv_the_raster text(200), uuc-srv__indices{}.x double, uuc-srv__indices{}.y double, uuc-srv__indices{}.z double, localhost_ObjectId mediumint, localhost_MetaId mediumint, localhost_SymbolId mediumint, localhost_the_raster text(200), localhost__indices{}.x double, localhost__indices{}.y double, localhost__indices{}.z double, _localhost_element_count text(20), _uuc-srv_element_count text(20), _concatenated_lh text, _concatenated_uuc text, antal_fel text, felmed text, _geometry text
Aggregator_3
    ACCUM_ATTRS_NAME = Drop Incoming Attributes
    AGGREGATE_TYPE = Homogeneous Collection (If Possible)
    COUNT_ATTR = _num
    MODE = Geometry - Assemble One Level
    SEP = ,
    AGGREGATE -> AttributeManager_5
AttributeManager_5
    ATTR_TABLE:
      SET_TO intrasisarchive = $(SourceDataset_POSTGIS_3)
      RENAME_SET_VALUE _num > object_olika_Z_antal
    -> FeatureMerger_3 [REQUESTOR]
Aggregator_4
    ACCUM_ATTRS_NAME = Drop Incoming Attributes
    AGGREGATE_TYPE = Homogeneous Collection (If Possible)
    COUNT_ATTR = _num
    MODE = Geometry - Assemble One Level
    SEP = ,
    AGGREGATE -> AttributeManager_6
AttributeManager_6
    ATTR_TABLE:
      SET_TO intrasisarchive = $(SourceDataset_POSTGIS_3)
      RENAME_SET_VALUE _num > object_samma_Z_antal
    -> FeatureMerger_3 [SUPPLIER]
FeatureMerger_3
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = @Value(intrasisarchive) @Value(intrasisarchive) AUTO
    MERGE_TYPE = Attributes Only
    PROCESS_DUPS = YES
    REJECT_NULL_MISSING_KEYS = No
    SUPPLIERS_FIRST = No
    MERGED -> FeatureMerger_2 [REQUESTOR]
    UNMERGED_REQUESTOR -> FeatureMerger_2 [REQUESTOR]
    UNUSED_SUPPLIER -> FeatureMerger_2 [REQUESTOR]
AttributeManager_7
    ATTR_TABLE = SET_TO intrasisarchive = $(SourceDataset_POSTGIS_3)
    USER_EXPOSED_ATTRIBUTES = _num
    -> testFilter_3_knas (writer OGCGEOPACKAGE_1)
testFilter_3_knas (writer OGCGEOPACKAGE_1)
    attributes: intrasisarchive text(200), uuc-srv_ObjectId mediumint, uuc-srv_MetaId mediumint, uuc-srv_SymbolId mediumint, uuc-srv_the_raster text(200), uuc-srv__indices{}.x double, uuc-srv__indices{}.y double, uuc-srv__indices{}.z double, localhost_ObjectId mediumint, localhost_MetaId mediumint, localhost_SymbolId mediumint, localhost_the_raster text(200), localhost__indices{}.x double, localhost__indices{}.y double, localhost__indices{}.z double, _localhost_element_count text(20), _uuc-srv_element_count text(20), _concatenated_lh text, _concatenated_uuc text, _geometry text, antal_fel text, felmed text
samma_Z_varde (writer OGCGEOPACKAGE_1)
    attributes: uuc-srv_ObjectId mediumint, uuc-srv_MetaId mediumint, uuc-srv_SymbolId mediumint, uuc-srv_the_raster text(200), uuc-srv__indices{}.x double, uuc-srv__indices{}.y double, uuc-srv__indices{}.z double, localhost_ObjectId mediumint, localhost_MetaId mediumint, localhost_SymbolId mediumint, localhost_the_raster text(200), localhost__indices{}.x double, localhost__indices{}.y double, localhost__indices{}.z double, _localhost_element_count text(20), _uuc-srv_element_count text(20), _concatenated_lh text, _concatenated_uuc text, _geometry text, antal_fel text, felmed text
Aggregator
    ACCUM_ATTRS_NAME = Drop Incoming Attributes
    AGGREGATE_TYPE = Homogeneous Collection (If Possible)
    COUNT_ATTR = _num
    MODE = Geometry - Assemble One Level
    SEP = ,
    AGGREGATE -> AttributeManager_2
AttributeManager_2
    ATTR_TABLE:
      SET_TO intrasisarchive = $(SourceDataset_POSTGIS_3)
      RENAME_SET_VALUE _num > object_utan_z_pa_uuc
    -> FeatureMerger_2 [SUPPLIER]
FeatureMerger_2
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = @Value(intrasisarchive) @Value(intrasisarchive) AUTO
    MERGE_TYPE = Attributes Only
    PROCESS_DUPS = YES
    REJECT_NULL_MISSING_KEYS = No
    SUPPLIERS_FIRST = No
    MERGED -> FeatureMerger_4 [REQUESTOR]
    UNMERGED_REQUESTOR -> FeatureMerger_4 [REQUESTOR]
    UNUSED_SUPPLIER -> FeatureMerger_4 [REQUESTOR]
FeatureMerger_4
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = @Value(intrasisarchive) @Value(intrasisarchive) AUTO
    MERGE_TYPE = Attributes Only
    PROCESS_DUPS = YES
    REJECT_NULL_MISSING_KEYS = No
    SUPPLIERS_FIRST = No
    MERGED -> antal_Z_per_intrasisarchhive (writer OGCGEOPACKAGE_1)
    UNMERGED_REQUESTOR -> antal_Z_per_intrasisarchhive (writer OGCGEOPACKAGE_1)
    UNUSED_SUPPLIER -> antal_Z_per_intrasisarchhive (writer OGCGEOPACKAGE_1)
antal_Z_per_intrasisarchhive (writer OGCGEOPACKAGE_1)
    attributes: intrasisarchive text(200), object_olika_Z_antal int, object_samma_Z_antal int, object_utan_z_pa_uuc int, object_med_olika_antal_z_varden int
