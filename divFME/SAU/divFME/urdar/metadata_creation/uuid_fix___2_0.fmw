FME workspace uuid_fix___2_0.fmw

Parameters:
- SourceDataset_OGCGEOPACKAGE = C:\Users\krima354\Box\Urdar\uuid_check\intrasis_archive_UUID_master.gpkg   # GeoPackage File
- SourceDataset_XLSXR = C:\Users\krima354\Box\Urdar\uuid_check\Kopia av urdar_site_list_prototype.xlsx   # Source Microsoft Excel File(s)
- SourceDataset_OGCGEOPACKAGE_4 = C:\Users\krima354\Box\Urdar\uuid_check\urdar_all_geom20240129.gpkg   # GeoPackage File
- SourceDataset_OGCGEOPACKAGE_7 = C:\Users\krima354\Box\Urdar\uuid_check\proj_info_20240119_2.gpkg   # GeoPackage File
- SourceDataset_OGCGEOPACKAGE_6 = C:\Users\krima354\Work Folders\Documents\kicki_arbetsfiler\GETdata\arkeologiska_uppdrag_undersökningsområden_sverig.gpkg   # GeoPackage File
- DestDataset_OGCGEOPACKAGE = C:\Users\krima354\Work Folders\Documents\kicki_arbetsfiler\urdar_arbetsfiler\create_siteinfo\site_info4.gpkg   # GeoPackage File

Readers:
- OGCGEOPACKAGE_1: OGCGEOPACKAGE from $(SourceDataset_OGCGEOPACKAGE) in EPSG:3006
- XLSXR_1: XLSXR from $(SourceDataset_XLSXR)
- OGCGEOPACKAGE_3: OGCGEOPACKAGE from $(SourceDataset_OGCGEOPACKAGE_4) in EPSG:3006
- OGCGEOPACKAGE_2: OGCGEOPACKAGE from $(SourceDataset_OGCGEOPACKAGE_7) in EPSG:3006
- OGCGEOPACKAGE_5: OGCGEOPACKAGE from $(SourceDataset_OGCGEOPACKAGE_6) in EPSG:3006

Writers:
- OGCGEOPACKAGE_4: OGCGEOPACKAGE to $(DestDataset_OGCGEOPACKAGE) in EPSG:3006

geom (reader OGCGEOPACKAGE_3)
    attributes: intrasis_archive text(200), id int,PrimaryKey
    -> GeometryFilter_3
GeometryFilter_3
    FILTER_MODE = SIMPLE
    FILTER_MULTI = FILTER_TYPES]Area]FME_CONTROLLER_QUERY_FILE]]FME_CONTROLLER_CHOICE]Simple
    Area -> Aggregator
    <UNFILTERED> -> Bufferer
Bufferer
    ANGLE = 22.5
    CAP_STYLE = Arc
    CORNER_STYLE = Arc
    MODE = AREA
    OFFSET = 0.01
    OFFSET_UNITS = METERS
    PRECISION = APPROX
    BUFFERED -> Aggregator
Aggregator
    ACCUM_ATTRS_NAME = Use Attributes From One Feature
    AGGREGATE_TYPE = Homogeneous Collection (If Possible)
    COUNT_ATTR = num_features
    GROUP_BY = intrasis_archive
    MODE = Geometry - Assemble One Level
    SEP = ,
    AGGREGATE -> FeatureMerger_3 [REQUESTOR]
UUID_master_final_20240125 (reader OGCGEOPACKAGE_1)
    attributes: master_site_archive text(17), master_site_name text(54), master_UUID text(37), master_UUID_finns text(200), link_master_uuid text(200), api_link_master_uuid text(200), master_Uppdaterat UUID text(37), master_Uppdaterat UUID_finns text(200), master_link_Uppdaterat_uuid text(200), api_link_master_Uppdaterat_uuid text(200), UUID_uu text(200), UUID_uu finns text(200), link_uuid_uu text(200), api_link_uuid_uu text(200), UUID_typ text(200), master_Kommentar text(685), ok_uu text(200), master_uppdrag_nr int, master_kmr_uppdragsnummer int, master_kmr_id text(37), master__length_uppdrag_nr text(200), master_uppdrag_ny text(200), start_typ text(200), status text(6), _count int, id int,PrimaryKey
    -> FeatureMerger [REQUESTOR]
UUID join (reader XLSXR_1)
    attributes: site_archive char(17), uppdrag_nr,N,10,0 number(7,0), UUID,C,64 char(37), Join string
    -> FeatureMerger [SUPPLIER]
FeatureMerger
    ATTR_ACCUM_MODE = Merge Supplier
    ATTR_CONFLICT_RES = Use Requestor
    IGNORE_NULLS = No
    JOIN_KEYS = @Value(master_site_archive) @Value(site_archive) AUTO
    MERGE_TYPE = Attributes Only
    PROCESS_DUPS = NO
    REJECT_NULL_MISSING_KEYS = No
    SUPPLIERS_FIRST = No
    MERGED -> FeatureMerger_3 [SUPPLIER]
    MERGED -> FeatureMerger_2 [SUPPLIER] [off]
    UNMERGED_REQUESTOR -> FeatureMerger_3 [SUPPLIER]
    <REJECTED> -> AttributeKeeper [off]
FeatureMerger_3
    ATTR_ACCUM_MODE = Merge Supplier
    ATTR_CONFLICT_RES = Use Requestor
    IGNORE_NULLS = No
    JOIN_KEYS = @Value(intrasis_archive) @Value(master_site_archive) AUTO
    MERGE_TYPE = Attributes Only
    PROCESS_DUPS = NO
    REJECT_NULL_MISSING_KEYS = No
    SUPPLIERS_FIRST = No
    MERGED -> TestFilter_4
    UNMERGED_REQUESTOR -> TestFilter_4
    UNUSED_SUPPLIER -> TestFilter_4
Note: lägger över UUIID_uu till master_UUID
TestFilter_4
    DEFAULT_VALUE = <UNFILTERED>
    PASSED_TEST_GROUP_OUTPUT = FIRST
    TEST_LIST = "BOOL_OP,OR,COMPOSITE_TEST,""""""1"""""",TEST_CLAUSE,TEST @Value(UUID_typ) = nytt förslag",@Value(UUID_typ) = UUID
    @Value(UUID_typ) = UUID -> AttributeManager
    <UNFILTERED> -> AttributeFilter
Note: lägger över UUIID_uu till master_UUID
AttributeManager
    ATTR_TABLE:
      SET_TO master_UUID = @Value(UUID_uu)
      SET_TO UUID_typ = UUID
    -> HTTPCaller
HTTPCaller
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://app.raa.se/open/fornsok/api/uppdrag/uppdrag/@Value(master_UUID)
    TRANSFER_TIMEOUT_LENGTH = 90
    USE_COOKIES = No
    VERIFY_SSL_CERTIFICATES = Yes
    -> AttributeManager_5
AttributeManager_5
    ATTR_TABLE = SET_TO master_UUID_finns = JA
    -> AttributeFilter
AttributeFilter
    ATTR_NAME = UUID_typ
    ATTR_VALUES = <Empty>,<Missing>,<Null>,<Unfiltered>,uppdaterat_UUID,UUID
    <MISSING> -> TestFilter_7
    <UNFILTERED> -> TestFilter_7
    uppdaterat_UUID -> TestFilter_5
    UUID -> AttributeManager_3
TestFilter_5
    DEFAULT_VALUE = <UNFILTERED>
    PASSED_TEST_GROUP_OUTPUT = FIRST
    TEST_LIST:
      "BOOL_OP,AND,COMPOSITE_TEST,""""""1 AND 2"""""",TEST_CLAUSE,TEST @Value(master_Uppdaterat UUID_finns) = JA
      TEST @Value(master_UUID_finns) = JA",@Value(master_Uppdaterat UUID_finns) = JA
    @Value(master_Uppdaterat UUID_finns) = JA -> AttributeManager_2
    <UNFILTERED> -> TestFilter_6
TestFilter_6
    DEFAULT_VALUE = <UNFILTERED>
    PASSED_TEST_GROUP_OUTPUT = FIRST
    TEST_LIST = "BOOL_OP,OR,COMPOSITE_TEST,""""""1"""""",TEST_CLAUSE,TEST @Value(master_Uppdaterat UUID_finns) = NEJ",@Value(master_Uppdaterat UUID_finns) = NEJ
    @Value(master_Uppdaterat UUID_finns) = NEJ -> AttributeManager_3
    <UNFILTERED> -> AttributeManager_2
AttributeManager_2
    ATTR_TABLE = SET_TO UUID_final = @Value(master_Uppdaterat UUID)
    USER_EXPOSED_ATTRIBUTES = UUID_final
    -> TestFilter_7
AttributeManager_3
    ATTR_TABLE = SET_TO UUID_final = @Value(master_UUID)
    USER_EXPOSED_ATTRIBUTES = UUID_final
    -> TestFilter_7
TestFilter_7
    DEFAULT_VALUE = <UNFILTERED>
    PASSED_TEST_GROUP_OUTPUT = FIRST
    TEST_LIST = "BOOL_OP,OR,COMPOSITE_TEST,""""""1"""""",TEST_CLAUSE,TEST UUID_final ATTRIBUTE_HAS_A_VALUE """,UUID_final has value
    UUID_final has value -> HTTPCaller_2
    <UNFILTERED> -> AttributeManager_4
HTTPCaller_2
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://app.raa.se/open/fornsok/api/uppdrag/uppdrag/@Value(UUID_final)
    TRANSFER_TIMEOUT_LENGTH = 90
    USE_COOKIES = No
    VERIFY_SSL_CERTIFICATES = Yes
    -> AttributeManager_6
    <REJECTED> -> AttributeManager_8
AttributeManager_6
    ATTR_TABLE = SET_TO UUID_final_finns = JA
    -> AttributeManager_4
AttributeManager_8
    ATTR_TABLE = SET_TO UUID_final_finns = NEJ
    -> AttributeManager_4
AttributeManager_4
    ATTR_TABLE:
      SET_TO master_site_archive = FME_CONDITIONAL:DEFAULT_VALUE'_FME_NO_OP_'BOOL_OP;OR;COMPOSITE_TEST;1;TEST @Value(intrasis_archive) = testremote'@Value(intrasis_archive)'FME_NUM_CONDITIONS2___
      SET_TO UUID_typ = FME_CONDITIONAL:DEFAULT_VALUE'_FME_NO_OP_'BOOL_OP;OR;COMPOSITE_TEST;1;TEST @Value(intrasis_archive) = testremote'extern'FME_NUM_CONDITIONS2___
      SET_TO UUID_final_link = FME_CONDITIONAL:DEFAULT_VALUE'_FME_NO_OP_'BOOL_OP;OR;COMPOSITE_TEST;1;TEST UUID_final ATTRIBUTE_HAS_A_VALUE _FME_BLANK_STRING_'https://app.raa.se/open/fornsok/uppdrag/@Value(UUID_final)'FME_NUM_CONDITIONS2___
      SET_TO link_master_uuid = FME_CONDITIONAL:DEFAULT_VALUE'_FME_NO_OP_'BOOL_OP;OR;COMPOSITE_TEST;1;TEST master_UUID ATTRIBUTE_HAS_A_VALUE _FME_BLANK_STRING_'https://app.raa.se/open/fornsok/uppdrag/@Value(master_UUID)'FME_NUM_CONDITIONS2___
      SET_TO master_link_Uppdaterat_uuid = FME_CONDITIONAL:DEFAULT_VALUE'_FME_NO_OP_'BOOL_OP;OR;COMPOSITE_TEST;1;TEST master_Uppdaterat UUID_finns ATTRIBUTE_HAS_A_VALUE _FME_BLANK_STRING_'https://app.raa.se/open/fornsok/uppdrag/@Value(master_Uppdaterat UUID)'FME_NUM_CONDITIONS2___
      REMOVE master_Kommentar
      REMOVE uppdrag_nr,N,10,0
      REMOVE ok_uu
      REMOVE master_uppdrag_nr
      REMOVE master_kmr_uppdragsnummer
      REMOVE master_kmr_id
      REMOVE master__length_uppdrag_nr
      REMOVE master_uppdrag_ny
      REMOVE start_typ
      REMOVE status
      REMOVE _count
      REMOVE id
      REMOVE site_archive
      REMOVE api_link_master_uuid
      REMOVE api_link_master_Uppdaterat_uuid
      REMOVE UUID_uu
      REMOVE link_uuid_uu
      REMOVE api_link_uuid_uu
      REMOVE Join
      REMOVE num_features
      REMOVE UUID,C,64
      REMOVE _response_body
      REMOVE _http_status_code
      REMOVE _error
      REMOVE fme_rejection_code
      REMOVE UUID_uu finns
    USER_EXPOSED_ATTRIBUTES = UUID_final_finns
    -> AttributeRemover
AttributeRemover
    REMOVE_ATTRS = intrasis_archive
    -> siteinfo (writer OGCGEOPACKAGE_4)
siteinfo (writer OGCGEOPACKAGE_4)
    attributes: master_site_archive text(17), master_site_name text(54), UUID_typ text(200), UUID_final text(37), UUID_final_finns text(200), UUID_final_link text(200), master_UUID text(37), master_UUID_finns text(200), link_master_uuid text(200), master_Uppdaterat UUID text(37), master_Uppdaterat UUID_finns text(200), master_link_Uppdaterat_uuid text(200)
point_median (reader OGCGEOPACKAGE_3)
    attributes: intrasis_archive text(200), id int,PrimaryKey
projec_information (reader OGCGEOPACKAGE_2)
    attributes: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

Bookmark: checking extra reference- ok
AttributeKeeper
    CREATE_BULK_MODE_FEATURES = NO
    KEEP_ATTRS = site_archive,site_name,UUID,C,64
    -> BulkAttributeRenamer
BulkAttributeRenamer
    ATTRCHOICE = All Attributes
    MODE_CHOICE = RENAME
    PATTERN_ACTION_DISP = ADDPREFIX
    REPLACE_STR = extre_ref_
    -> FeatureMerger_2 [REQUESTOR]
FeatureMerger_2
    ATTR_ACCUM_MODE = Merge Supplier
    ATTR_CONFLICT_RES = Use Requestor
    IGNORE_NULLS = No
    JOIN_KEYS = @Value(extre_ref_site_archive) @Value(master_site_archive) AUTO
    MERGE_TYPE = Attributes Only
    PROCESS_DUPS = NO
    REJECT_NULL_MISSING_KEYS = No
    SUPPLIERS_FIRST = No
    MERGED -> AttributeManager_7
AttributeManager_7
    -> TestFilter_2
TestFilter_2
    DEFAULT_VALUE = <UNFILTERED>
    PASSED_TEST_GROUP_OUTPUT = FIRST
    TEST_LIST = "BOOL_OP,OR,COMPOSITE_TEST,""""""1"""""",TEST_CLAUSE,TEST @Value(UUID,C,64) = @Value(extre_ref_UUID,C,64)",UUID,C,64 = extre_ref_UUID,C,64
    <UNFILTERED> -> TestFilter_3
TestFilter_3
    DEFAULT_VALUE = <UNFILTERED>
    PASSED_TEST_GROUP_OUTPUT = FIRST
    TEST_LIST = "BOOL_OP,OR,COMPOSITE_TEST,""""""1"""""",TEST_CLAUSE,TEST @Value(master_UUID) = @Value(UUID,C,64)",@Value(master_UUID) = UUID,C,64
    <UNFILTERED> -> TestFilter_10
TestFilter_10
    DEFAULT_VALUE = <UNFILTERED>
    PASSED_TEST_GROUP_OUTPUT = FIRST
    TEST_LIST = "BOOL_OP,OR,COMPOSITE_TEST,""""""1"""""",TEST_CLAUSE,TEST @Value(master_UUID) = @Value(extre_ref_UUID,C,64)",@Value(master_UUID) = @Value(extre_ref_UUID,C,64)
    <UNFILTERED> -> HTTPCaller_3
HTTPCaller_3
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body_UUID_C64
    TARGET_ATTR_ENCODING = auto-detect
    TARGET_URL = https://app.raa.se/open/fornsok/api/uppdrag/uppdrag/@Value(extre_ref_UUID,C,64)
    TRANSFER_TIMEOUT_LENGTH = 90
    USE_COOKIES = No
    VERIFY_SSL_CERTIFICATES = Yes
    -> TestFilter
TestFilter
    DEFAULT_VALUE = <UNFILTERED>
    PASSED_TEST_GROUP_OUTPUT = FIRST

Bookmark: rest
TestFilter_8
    DEFAULT_VALUE = <UNFILTERED>
    PASSED_TEST_GROUP_OUTPUT = FIRST
    TEST_LIST = "BOOL_OP,OR,COMPOSITE_TEST,""""""1"""""",TEST_CLAUSE,TEST @Value(UUID_final) = @Value(UUID,C,64)",@Value(UUID_final) = @Value(UUID,C,64)
    <UNFILTERED> -> TestFilter_9
TestFilter_9
    DEFAULT_VALUE = <UNFILTERED>
    PASSED_TEST_GROUP_OUTPUT = FIRST
    TEST_LIST = "BOOL_OP,OR,COMPOSITE_TEST,""""""1"""""",TEST_CLAUSE,TEST UUID_final ATTRIBUTE_HAS_A_VALUE """,UUID_final ATTRIBUTE_HAS_A_VALUE

Bookmark: uo-används ej
arkeologiska_uppdrag_undersökningsområden_sverige_point (reader OGCGEOPACKAGE_5)
    attributes: id text(255), uppdragsnummer text(9), beslutande_myndighet text(255), beslutsdatum date, diarienummer text(255), uppdragstyp text(255), utforande_organisation text(255), nollresultat text(9), url text(255), status text(255), lan text, kommun text, socken text, fid int,PrimaryKey
    -> FeatureMerger_4 [SUPPLIER]
arkeologiska_uppdrag_undersökningsområden_sverige_linestring (reader OGCGEOPACKAGE_5)
    attributes: id text(255), uppdragsnummer text(9), beslutande_myndighet text(255), beslutsdatum date, diarienummer text(255), uppdragstyp text(255), utforande_organisation text(255), nollresultat text(9), url text(255), status text(255), lan text, kommun text, socken text, fid int,PrimaryKey
    -> FeatureMerger_4 [SUPPLIER]
arkeologiska_uppdrag_undersökningsområden_sverige_polygon (reader OGCGEOPACKAGE_5)
    attributes: id text(255), uppdragsnummer text(9), beslutande_myndighet text(255), beslutsdatum date, diarienummer text(255), uppdragstyp text(255), utforande_organisation text(255), nollresultat text(9), url text(255), status text(255), lan text, kommun text, socken text, fid int,PrimaryKey
    -> FeatureMerger_4 [SUPPLIER]
FeatureMerger_4
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = @Value(UUID_final) @Value(id) AUTO
    MERGE_COUNT_ATTR = num_suplier
    MERGE_TYPE = Attributes and Geometry
    PROCESS_DUPS = YES
    REJECT_NULL_MISSING_KEYS = No
    SUPPLIERS_FIRST = No
