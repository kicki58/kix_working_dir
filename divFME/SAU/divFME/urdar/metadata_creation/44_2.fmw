FME workspace 44_2.fmw

Parameters:
- SourceDataset_XLSXR = C:\Users\krima354\Downloads\Raderade uppdrag_ny.xlsx   # Source Microsoft Excel File(s)
- SourceDataset_XLSXR_3 = C:\Users\krima354\Downloads\urdar_site_list_prototype.xlsx   # Source Microsoft Excel File(s)
- SourceDataset_OGCGEOPACKAGE = C:\Users\krima354\Work Folders\Documents\kicki_arbetsfiler\urdar_arbetsfiler\create_siteinfo\fyrtiofyra.gpkg   # GeoPackage File

Readers:
- XLSXR_1: XLSXR from $(SourceDataset_XLSXR)
- XLSXR_2: XLSXR from $(SourceDataset_XLSXR_3)
- OGCGEOPACKAGE_1: OGCGEOPACKAGE from $(SourceDataset_OGCGEOPACKAGE)

jsonformatter (1) (reader XLSXR_1)
    attributes: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
dap_urdar_all_rows (reader XLSXR_2)
    attributes: site_name char(43), site_archive char(17), parish_name char(20), lan_name char(24), pk number(5,0), uppdrag_nr,N,10,0 number(7,0), titel,C,254 char(275), und_typ,C,64 char(55), arende,C,128 char(31), dnr_lst,C,16 char(17), dnr_utf,C,16 char(19), lan,C,64 char(24), landskap,C,64 char(15), kommun,C,64 char(16), socken,C,64 char(20), lokal,C,200 char(54), fornl_nr,C,32 char(36), fornl_kat,C,32 string, FMIS_id,N,20,0 string, und_fornl,C,128 char(40), kontext,C,64 string, datering,C,164 char(61), ansvarig,C,64 char(61), deltagare,C,254 string, und_ar,C,16 number(5,0), und_tid,C,32 string, und_yta,N,16,6 string, referens,C,254 char(30), rapport,C,254 char(58), databasnamn char(27),
      ovrigt,C,249 string, osaker,C,3 char(4), precision,C,16 char(13), ursprung,C,64 char(27), UUID,C,64 char(37)
    -> TestFilter_2
TestFilter_2
    DEFAULT_VALUE = <UNFILTERED>
    PASSED_TEST_GROUP_OUTPUT = FIRST
    TEST_LIST = "BOOL_OP,OR,COMPOSITE_TEST,""""""1"""""",TEST_CLAUSE,TEST site_archive ATTRIBUTE_HAS_A_VALUE """,site_archive ATTRIBUTE_HAS_A_VALUE
    site_archive ATTRIBUTE_HAS_A_VALUE -> FeatureMerger [SUPPLIER]
    site_archive ATTRIBUTE_HAS_A_VALUE -> BulkAttributeRenamer_2
BulkAttributeRenamer_2
    ATTRCHOICE = All Attributes
    MODE_CHOICE = RENAME
    PATTERN_ACTION_DISP = ADDPREFIX
    REPLACE_STR = ar_
    -> FeatureMerger_3 [SUPPLIER]
UUID join (reader XLSXR_2)
    attributes: site_archive char(17), uppdrag_nr,N,10,0 number(7,0), UUID,C,64 char(37), Join string
    -> BulkAttributeRenamer
BulkAttributeRenamer
    ATTRCHOICE = All Attributes
    MODE_CHOICE = RENAME
    PATTERN_ACTION_DISP = ADDPREFIX
    REPLACE_STR = join_
    -> FeatureMerger [REQUESTOR]
FeatureMerger
    ATTR_ACCUM_MODE = Merge Supplier
    ATTR_CONFLICT_RES = Use Requestor
    IGNORE_NULLS = No
    JOIN_KEYS = @Value(join_site_archive) @Value(site_archive) AUTO
    MERGE_TYPE = Attributes Only
    PROCESS_DUPS = NO
    REJECT_NULL_MISSING_KEYS = No
    SUPPLIERS_FIRST = No
    MERGED -> TestFilter
    <REJECTED> -> FeatureMerger_3 [REQUESTOR]
TestFilter
    DEFAULT_VALUE = <UNFILTERED>
    PASSED_TEST_GROUP_OUTPUT = FIRST
    TEST_LIST = "BOOL_OP,OR,COMPOSITE_TEST,""""""1"""""",TEST_CLAUSE,TEST @Value(join_UUID,C,64) = @Value(UUID,C,64)",@Value(join_UUID,C,64) = @Value(UUID,C,64)
    @Value(join_UUID,C,64) = @Value(UUID,C,64) -> FeatureMerger_2 [SUPPLIER]
FeatureMerger_3
    ATTR_ACCUM_MODE = Merge Supplier
    ATTR_CONFLICT_RES = Use Requestor
    IGNORE_NULLS = No
    JOIN_KEYS = @Value(site_archive) @Value(ar_site_archive) AUTO
    MERGE_TYPE = Attributes Only
    PROCESS_DUPS = NO
    REJECT_NULL_MISSING_KEYS = No
    SUPPLIERS_FIRST = No
    MERGED -> AttributeKeeper
AttributeKeeper
    CREATE_BULK_MODE_FEATURES = NO
    KEEP_ATTRS = ar_UUID,C,64,UUID,C,64,ar_site_archive,site_archive
    -> TestFilter_3
TestFilter_3
    DEFAULT_VALUE = <UNFILTERED>
    PASSED_TEST_GROUP_OUTPUT = FIRST
    TEST_LIST = "BOOL_OP,OR,COMPOSITE_TEST,""""""1"""""",TEST_CLAUSE,TEST @Value(ar_UUID,C,64) = @Value(UUID,C,64)",@Value(join_UUID,C,64) = @Value(UUID,C,64)
44_4 (reader OGCGEOPACKAGE_1)
    attributes: master_site_archive text(17), _part_number text(20), _feature_number int, _vertex_number int, _x text(200), _y text(200), _z text, intrasis_archive text(200), master_site_name text(54), UUID_final text(37), UUID_final_link text(200), UUID_typ text(200), UUID,C,64 text(37), UUID,C,64_link text(200), master_Kommentar text(685), master_UUID_finns text(200), master_Uppdaterat UUID_finns text(200), _error text, fme_rejection_code text, _response_body_UUID_C64 text, _http_status_code text, id int,PrimaryKey
    -> FeatureMerger_2 [REQUESTOR]
FeatureMerger_2
    ATTR_ACCUM_MODE = Merge Supplier
    ATTR_CONFLICT_RES = Use Requestor
    IGNORE_NULLS = No
    JOIN_KEYS = @Value(intrasis_archive) @Value(join_site_archive) AUTO
    MERGE_TYPE = Attributes Only
    PROCESS_DUPS = NO
    REJECT_NULL_MISSING_KEYS = No
    SUPPLIERS_FIRST = No
    MERGED -> AttributeKeeper_2
AttributeKeeper_2
    CREATE_BULK_MODE_FEATURES = NO
    KEEP_ATTRS = UUID_final,UUID,C,64
