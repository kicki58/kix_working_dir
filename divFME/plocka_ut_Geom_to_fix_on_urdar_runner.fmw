FME workspace plocka_ut_Geom_to_fix_on_urdar_runner.fmw

Parameters:
- SourceDataset_CSV2 = C:\Users\krima354\Work Folders\Documents\kicki_arbetsfiler\slask\no_project_info.csv   # Source CSV (Comma Separated Value) File(s)
- USER_NAME_POSTGIS = kicki   # Username
- PASSWORD =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   # Password
- DestDataset_OGCGEOPACKAGE = C:\Users\krima354\Work Folders\Documents\kicki_arbetsfiler\slask\32_from_urdar.gpkg   # GeoPackage File
- HOST_POSTGIS = 130.238.10.179   # Host
- PORT_POSTGIS = 5432   # Port

Readers:
- CSV2_1: CSV2 from $(SourceDataset_CSV2)

CSV (reader CSV2_1)
    attributes: databas varchar(10), num_tables uint32, gpkg-file varchar(102), Beskrivning varchar(1), Exploateringstyp varchar(1), fid varchar(1), Inventarienummer varchar(1), Lst Dnr varchar(1), pk varchar(1), Plats varchar(1), Projektkod varchar(1), Projektledare varchar(1), Projektnamn varchar(1), Raä Dnr varchar(1), SiteId varchar(1), Slutdatum varchar(1), Undersökningstyp varchar(1), Uppdragsgivare varchar(1), _reader_error varchar(59)
    -> WorkspaceRunner
WorkspaceRunner
    BLOCKING = Yes
    WORKSPACE_FILE = $(FME_MF_DIR)plocka_ut_Geom_to_fix_on_urdar.fmw
    WORKSPACE_PARAMETERS = SourceDataset_POSTGIS_2,@Value(databas),USER_NAME_POSTGIS,$(USER_NAME_POSTGIS),PASSWORD,$(PASSWORD),DestDataset_OGCGEOPACKAGE,$(DestDataset_OGCGEOPACKAGE),HOST_POSTGIS,$(HOST_POSTGIS),PORT_POSTGIS,$(PORT_POSTGIS)
