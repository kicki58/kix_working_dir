FME workspace checkDIFF_geom_runner.fmw

Parameters:
- SourceDataset_OGCGEOPACKAGE = C:\Users\krima354\Work Folders\Documents\kicki_arbetsfiler\urdar_arbetsfiler\create_siteinfo\Fixed geometries2\jmfr_shape_urdar.gpkg   # GeoPackage File

Readers:
- OGCGEOPACKAGE_1: OGCGEOPACKAGE from $(SourceDataset_OGCGEOPACKAGE)

bounding_box (reader OGCGEOPACKAGE_1)
    attributes: sitearchive text(200), from text(200), fid_1 double, intrasis_a text(254), object_ids text(254), occurrence text(254), pk mediumint, id int,PrimaryKey
    -> TestFilter
TestFilter
    DEFAULT_VALUE = <UNFILTERED>
    PASSED_TEST_GROUP_OUTPUT = FIRST
    TEST_LIST = "BOOL_OP,OR,COMPOSITE_TEST,""""""1"""""",TEST_CLAUSE,TEST @Value(from) = urdar",urdar,"BOOL_OP,OR,COMPOSITE_TEST,""""""1"""""",TEST_CLAUSE,TEST @Value(from) = shape",shape
    urdar -> AreaCalculator
    shape -> AreaCalculator_2
AreaCalculator
    AREA_ATTR = _area_urdar
    AREA_TYPE = Plane Area
    MULT = 1
    -> FeatureMerger [REQUESTOR]
AreaCalculator_2
    AREA_ATTR = _area_shape
    AREA_TYPE = Plane Area
    MULT = 1
    -> FeatureMerger [SUPPLIER]
FeatureMerger
    ATTR_ACCUM_MODE = Merge Supplier
    ATTR_CONFLICT_RES = Use Requestor
    IGNORE_NULLS = No
    JOIN_KEYS = @Value(sitearchive) @Value(sitearchive) AUTO
    MERGE_TYPE = Attributes Only
    PROCESS_DUPS = NO
    REJECT_NULL_MISSING_KEYS = No
    SUPPLIERS_FIRST = No
    MERGED -> TestFilter_2
TestFilter_2
    DEFAULT_VALUE = <UNFILTERED>
    PASSED_TEST_GROUP_OUTPUT = FIRST
    TEST_LIST = "BOOL_OP,OR,COMPOSITE_TEST,""""""1"""""",TEST_CLAUSE,TEST @Evaluate(@round(@Value(_area_shape),5)) = @Evaluate(@round(@Value(_area_urdar),5))",lika
    lika -> Inspector_2
Inspector_2
Inspector
