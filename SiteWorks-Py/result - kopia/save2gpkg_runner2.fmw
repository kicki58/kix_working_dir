FME workspace save2gpkg_runner2.fmw

Parameters:
- SourceDataset_PATH = C:\Github\kix\SiteWorks-Py\result   # INCLUDE_WEB_BROWSER Source Folder and File Pathnames Folder

Readers:
- PATH_1: PATH from $(SourceDataset_PATH)

PATH (reader PATH_1)
    attributes: path_unix buffer, path_windows buffer, path_rootname buffer, path_filename buffer, path_extension buffer, path_directory_unix buffer, path_directory_windows buffer, path_type char(10)
    -> AttributeManager
    -> AttributeManager_2
    -> Tester
AttributeManager
    ATTR_TABLE:
      SET_TO path_to_csv = @Value(path_windows)\csv
      SET_TO gpkg_file =  @Value(path_directory_windows)@Value(path_filename).gpkg
      SET_TO path_to_csv2 = ..\..\SiteWorks-Py\result
      SET_TO gpkg_file2 = ..\..\SiteWorks-Py\gpkg\@Value(path_filename).gpkg
Tester
    BOOL_OP = OR
    TEST_CLAUSE = TEST @Value(path_filename) = 2985 Mesta 6 U
    TEST_MODE = TEST
    PASSED -> AttributeManager_3
AttributeManager_3
    ATTR_TABLE:
      SET_TO path_to_csv = @Value(path_windows)\csv
      SET_TO gpkg_file =  @Value(path_directory_windows)@Value(path_filename).gpkg
      SET_TO path_to_csv2 = ..\..\SiteWorks-Py\result
      SET_TO gpkg_file2 = ..\..\SiteWorks-Py\gpkg\@Value(path_filename).gpkg
    -> WorkspaceRunner
WorkspaceRunner
    BLOCKING = No
    MAX_TO_BATCH = 1
    WORKSPACE_FILE = .\save2gpkg.fmw
    WORKSPACE_PARAMETERS = csv_folder,@Value(path_to_csv),db_name,@Value(path_filename),DestDataset_OGCGEOPACKAGE,@Value(gpkg_file),SourceDataset_CSV2_43,$(csv_folder2)\OBJDATA.csv,SourceDataset_CSV2_65,$(csv_folder2)\ACCURACY.csv,SourceDataset_CSV2_49,$(csv_folder2)\ARCHIVE.csv,SourceDataset_CSV2_41,$(csv_folder2)\COLOURDEF.csv,SourceDataset_CSV2,$(csv_folder2)\CLASSDEF.csv,SourceDataset_CSV2_57,$(csv_folder2)\COUNTY.csv,SourceDataset_CSV2_73,$(csv_folder2)\DATINGMETHOD.csv,SourceDataset_CSV2_45,$(csv_folder2)\DATINGPERIOD.csv,SourceDataset_CSV2_53,$(csv_folder2)\DECORDEF.csv,SourceDataset_CSV2_61,$(csv_folder2)\DEFDEF.csv,SourceDataset_CSV2_69,$(csv_folder2)\ELMTYPE.csv,SourceDataset_CSV2_39,$(csv_folder2)\LAYER.csv,SourceDataset_CSV2_47,$(csv_folder2)\MATDEF.csv,SourceDataset_CSV2_51,$(csv_folder2)\MTYPE.csv,SourceDataset_CSV2_55,$(csv_folder2)\MUNICIPALITY.csv,SourceDataset_CSV2_59,$(csv_folder2)\OBJ.csv,SourceDataset_CSV2_63,$(csv_folder2)\OBJDETAIL.csv,SourceDataset_CSV2_67,$(csv_folder2)\OBJECT.csv,SourceDataset_CSV2_71,$(csv_folder2)\OBJTY.csv,SourceDataset_CSV2_38,$(csv_folder2)\OBJTYPPROJ.csv,SourceDataset_CSV2_40,$(csv_folder2)\PARTDEF.csv,SourceDataset_CSV2_42,$(csv_folder2)\PATTY.csv,SourceDataset_CSV2_44,$(csv_folder2)\PROCESSDEF.csv,SourceDataset_CSV2_46,$(csv_folder2)\PROJECT.csv,SourceDataset_CSV2_48,$(csv_folder2)\PROJSTAFF.csv,SourceDataset_CSV2_50,$(csv_folder2)\PROJTASK.csv,SourceDataset_CSV2_52,$(csv_folder2)\PROJTYPE.csv,SourceDataset_CSV2_54,$(csv_folder2)\PROVINCE.csv,SourceDataset_CSV2_56,$(csv_folder2)\QUERIE.csv,SourceDataset_CSV2_58,$(csv_folder2)\RELATION.csv,SourceDataset_CSV2_60,$(csv_folder2)\SHAPEDEF.csv,SourceDataset_CSV2_62,$(csv_folder2)\SPECREGDEF.csv,SourceDataset_CSV2_64,$(csv_folder2)\STAFF.csv,SourceDataset_CSV2_66,$(csv_folder2)\STRATA.csv,SourceDataset_CSV2_68,$(csv_folder2)\SYSDATA.csv,SourceDataset_CSV2_70,$(csv_folder2)\TECHNIQUEDEF.csv,SourceDataset_CSV2_72,$(csv_folder2)\WEARDEF.csv
AttributeManager_2
    ATTR_TABLE:
      RENAME_SET_VALUE path_filename > db_name
      SET_TO gpkg_file = $(SourceDataset_PATH)\gpkg\@Value(db_name).gpkg
    -> FeatureReader [INITIATOR]
FeatureReader
    ATTRIBUTES = PATH,"path_unix,path_windows,path_rootname,path_filename,path_extension,path_directory_unix,path_directory_windows,path_type,fme_geometry{0}"
    ATTR_ACCUM_MODE = Prefix Initiator
    ATTR_PREFIX = path1_
    COMBINE_GEOM = Use Result
    DATASET = @Value(path_windows)
    FORMAT = PATH
    OUTPUT_FEATURES_DISPLAY = Schema and Data Features
    PATH_GLOB_PATTERN = *
    PATH_NO_EMPTY_PROPERTIES = YES
    PATH_OFFSET_DATETIME = yes
    PATH_RECURSE_DIRECTORIES = NO
    PATH_RETRIEVE_FILE_PROPERTIES = NO
    PATH_TYPE = DIRECTORY
    PATH_USE_NON_STRING_ATTR = yes
