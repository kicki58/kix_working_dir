FME workspace unika_fr_hopslagning'.fmw

Parameters:
- SourceDataset_XLSXR = $(FME_MF_DIR)alla_c14_2.xlsx   # Source Microsoft Excel File(s)
- FEATURE_TYPES =
- DestDataset_XLSXW = $(FME_MF_DIR)alla_c14_unika.xlsx   # Destination Microsoft Excel File

Readers:
- XLSXR_1: XLSXR from $(SourceDataset_XLSXR)

Writers:
- XLSXW_1: XLSXW to $(DestDataset_XLSXW)

Blad1 (reader XLSXR_1)
    attributes: Socken char(22), By/Gård char(40), RAÄ-nr char(15), Fornlämningstyp char(29), Fält1 char(21), LandId char(4), Labnr char(22), 14Cålder number(5,0), Stdav number(4,0), 13C number(6,2), Modern char(15), Kommentar char(95), Bedömd relevant char(2), Sort char(29), Art 1 char(26), Art 2 char(11), Anlnr char(15), Anläggning char(33), Författare char(51), Tryckår number(5,0), Titel char(217), Tidskrift char(97), Förlagsort char(16)
    -> DuplicateFilter
DuplicateFilter
    INPUT_ORDERED_CHOICE = No
    KEYATTR = Labnr
    UNIQUE -> Blad1 (writer XLSXW_1)
Blad1 (writer XLSXW_1)
    attributes: Socken string(22), By/Gård string(40), RAÄ-nr string(15), Fornlämningstyp string(29), Fält1 string(21), LandId string(4), Labnr string(22), 14Cålder number(5), Stdav number(4), 13C number(6), Modern string(15), Kommentar string(95), Bedömd relevant string(2), Sort string(29), Art 1 string(26), Art 2 string(11), Anlnr string(15), Anläggning string(33), Författare string(51), Tryckår number(5), Titel string(217), Tidskrift string(97), Förlagsort string(16)
