FME workspace 2_insert2dapSchemaMapping.fmw

Parameters:
- SourceDataset_GENERIC = ""C:\Users\krima354\Box\SweDigArch M3\Indata\DAP\Sakarias Arbetsmaterial\Omprojicerad och bearbetad data\Gävleborg 2\Länsmuseet Gävleborg_2004_01 Måndagsbäcken\A1_2.shp" "C:\Users\krima354\Box\SweDigArch M3\Indata\DAP\Sakarias Arbetsmaterial\Omprojicerad och bearbetad data\Gävleborg 2\Länsmuseet Gävleborg_2004_01 Måndagsbäcken\A2.shp" "C:\Users\krima354\Box\SweDigArch M3\Indata\DAP\Sakarias Arbetsmaterial\Omprojicerad och bearbetad data\Gävleborg 2\Länsmuseet Gävleborg_2004_01 Måndagsbäcken\Höjder.shp" "C:\Users\krima354\Box\SweDigArch M3\Indata\DAP\Sakarias Arbetsmaterial\Omprojicerad och bearbetad data\Gävleborg 2\Länsmuseet Gävleborg_2004_01 Måndagsbäcken\Höjder_2.shp" "C:\Users\krima354\Box\SweDigArch M3\Indata\DAP\Sakarias Arbetsmaterial\Omprojicerad och bearbetad data\Gävleborg 2\Länsmuseet Gävleborg_2004_01 Måndagsbäcken\Schakt F.shp" "C:\Users\krima354\Box\SweDigArch M3\Indata\DAP\Sakarias Arbetsmaterial\Omprojicerad och bearbetad data\Gävleborg 2\Länsmuseet Gävleborg_2004_01 Måndagsbäcken\Schakt.shp" "C:\Users\krima354\Box\SweDigArch M3\Indata\DAP\Sakarias Arbetsmaterial\Omprojicerad och bearbetad data\Gävleborg 2\Länsmuseet Gävleborg_2004_01 Måndagsbäcken\Schakt_N.shp" "C:\Users\krima354\Box\SweDigArch M3\Indata\DAP\Sakarias Arbetsmaterial\Omprojicerad och bearbetad data\Gävleborg 2\Länsmuseet Gävleborg_2004_01 Måndagsbäcken\Sten_ytaB.shp" "C:\Users\krima354\Box\SweDigArch M3\Indata\DAP\Sakarias Arbetsmaterial\Omprojicerad och bearbetad data\Gävleborg 2\Länsmuseet Gävleborg_2004_01 Måndagsbäcken\Sten_ytaB_2.shp" "C:\Users\krima354\Box\SweDigArch M3\Indata\DAP\Sakarias Arbetsmaterial\Omprojicerad och bearbetad data\Gävleborg 2\Länsmuseet Gävleborg_2004_01 Måndagsbäcken\Sten_ytaB_3.shp" "C:\Users\krima354\Box\SweDigArch M3\Indata\DAP\Sakarias Arbetsmaterial\Omprojicerad och bearbetad data\Gävleborg 2\Länsmuseet Gävleborg_2004_01 Måndagsbäcken\Sten_ytaBD.shp" "C:\Users\krima354\Box\SweDigArch M3\Indata\DAP\Sakarias Arbetsmaterial\Omprojicerad och bearbetad data\Gävleborg 2\Länsmuseet Gävleborg_2004_01 Måndagsbäcken\Sten_ytaBD_2.shp" "C:\Users\krima354\Box\SweDigArch M3\Indata\DAP\Sakarias Arbetsmaterial\Omprojicerad och bearbetad data\Gävleborg 2\Länsmuseet Gävleborg_2004_01 Måndagsbäcken\Sten_ytaC.shp" "C:\Users\krima354\Box\SweDigArch M3\Indata\DAP\Sakarias Arbetsmaterial\Omprojicerad och bearbetad data\Gävleborg 2\Länsmuseet Gävleborg_2004_01 Måndagsbäcken\Sten_ytaC2.shp" "C:\Users\krima354\Box\SweDigArch M3\Indata\DAP\Sakarias Arbetsmaterial\Omprojicerad och bearbetad data\Gävleborg 2\Länsmuseet Gävleborg_2004_01 Måndagsbäcken\Sten_ytaD.shp" "C:\Users\krima354\Box\SweDigArch M3\Indata\DAP\Sakarias Arbetsmaterial\Omprojicerad och bearbetad data\Gävleborg 2\Länsmuseet Gävleborg_2004_01 Måndagsbäcken\Sten_ytaD_2.shp" "C:\Users\krima354\Box\SweDigArch M3\Indata\DAP\Sakarias Arbetsmaterial\Omprojicerad och bearbetad data\Gävleborg 2\Länsmuseet Gävleborg_2004_01 Måndagsbäcken\Sten_ytaE.shp" "C:\Users\krima354\Box\SweDigArch M3\Indata\DAP\Sakarias Arbetsmaterial\Omprojicerad och bearbetad data\Gävleborg 2\Länsmuseet Gävleborg_2004_01 Måndagsbäcken\Totalkvarts.shp" "C:\Users\krima354\Box\SweDigArch M3\Indata\DAP\Sakarias Arbetsmaterial\Omprojicerad och bearbetad data\Gävleborg 2\Länsmuseet Gävleborg_2004_01 Måndagsbäcken\totalkvartsit.shp""   # Source Dataset
- FEATURE_TYPES = A1_2 A2 Höjder Höjder_2 Schakt Schakt F Schakt_N Sten_ytaB Sten_ytaB_2 Sten_ytaB_3 Sten_ytaBD Sten_ytaBD_2 Sten_ytaC Sten_ytaC2 Sten_ytaD Sten_ytaD_2 Sten_ytaE Totalkvarts totalkvartsit
- DestDataset_POSTGIS = kicki@dap_data   # Connection

Readers:
- GENERIC_1: GENERIC from $(SourceDataset_GENERIC)

Writers:
- POSTGIS_1: POSTGIS to $(DestDataset_POSTGIS)

A1_2 (reader GENERIC_1)
    attributes: mÃƒÂ¥a1 varchar(10), UUID varchar(51), N1 real64, N2 int32, N3 real64, N4 real64, N5 real64, N6 real64, N7 real64, mÃƒÂ¥a2 varchar(10), mÃƒÂ¥b1 varchar(10), mÃƒÂ¥bd varchar(10), mÃƒÂ¥c1 varchar(10), mÃƒÂ¥c1x varchar(10), mÃƒÂ¥d1 varchar(10), mÃƒÂ¥e1 varchar(10), mÃƒÂ¥f1 varchar(10), mÃƒÂ¥h varchar(10), mÃƒÂ¥h2 varchar(10)
    -> SchemaMapper
SchemaMapper
    CSV2_CASE_SENSITIVE_FIELD_NAMES = Yes
    CSV2_CHUNK_SIZE = 100000
    CSV2_DATA_START_LINE = 2
    CSV2_DATE_INPUT_FORMAT = ISO
    CSV2_DELIMITER = auto
    CSV2_ENCODING = windows-1252
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = No
    CSV2_SCAN_ADDITIONAL_FIELDS = No
    CSV2_SCAN_MAX_ROWS = 10000
    CSV2_SCAN_TYPES = Yes
    CSV2_SKIP_DUPLICATE_DELIMITERS = No
    CSV2_STRING_TYPE_ATTRIBUTE_HANDLING = EXPLICIT_WIDTH
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_TYPE_ATTRIBUTE_HANDLING = STANDARD_TYPES
    CSV2_USE_CUSTOM_SCHEMA = NO
    DATASET = C:\Users\krima354\Work Folders\Documents\slask\AttributeMappingTable.csv
    FORMAT = CSV2
    IDXDESTATTR = fme_feature_type
    IDXDESTCOL = ""
    IDXSOURCEATTR = fme_feature_type
    IDXSOURCECOL = ""
    MAP_ATTRS = SourceAttribute DestinationAttribute $(FME_ASC_16)
    ROW_ID_ATTR = _schemamapper_row_ids
    TABLE = CSV
    MAPPED -> AttributeManager
AttributeManager
    -> features (writer POSTGIS_1)
features (writer POSTGIS_1)
    attributes: id serial,PrimaryKey, pk int4, uppdragsnr_lstnr text, object_id int4, object_name text, class text, subclass text, spatial_type text, attributes text, object_description text, group_name text, group_description text
