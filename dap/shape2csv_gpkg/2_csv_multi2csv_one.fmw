FME workspace 2_csv_multi2csv_one.fmw

Parameters:
- SourceDataset_CSV2 = ""C:\Users\krima354\Work Folders\Documents\kicki_arbetsfiler\dap\utdata\lerharen\ohar_generic8\lerharen_oharm_generic_csv\Anläggningar.csv" "C:\Users\krima354\Work Folders\Documents\kicki_arbetsfiler\dap\utdata\lerharen\ohar_generic8\lerharen_oharm_generic_csv\Anläggningar_2.csv" "C:\Users\krima354\Work Folders\Documents\kicki_arbetsfiler\dap\utdata\lerharen\ohar_generic8\lerharen_oharm_generic_csv\Eldgivning.csv" "C:\Users\krima354\Work Folders\Documents\kicki_arbetsfiler\dap\utdata\lerharen\ohar_generic8\lerharen_oharm_generic_csv\Enhet.csv" "C:\Users\krima354\Work Folders\Documents\kicki_arbetsfiler\dap\utdata\lerharen\ohar_generic8\lerharen_oharm_generic_csv\Krypgångar.csv" "C:\Users\krima354\Work Folders\Documents\kicki_arbetsfiler\dap\utdata\lerharen\ohar_generic8\lerharen_oharm_generic_csv\Kulle.csv" "C:\Users\krima354\Work Folders\Documents\kicki_arbetsfiler\dap\utdata\lerharen\ohar_generic8\lerharen_oharm_generic_csv\Kulle_2.csv" "C:\Users\krima354\Work Folders\Documents\kicki_arbetsfiler\dap\utdata\lerharen\ohar_generic8\lerharen_oharm_generic_csv\siteinfo.csv" "C:\Users\krima354\Work Folders\Documents\kicki_arbetsfiler\dap\utdata\lerharen\ohar_generic8\lerharen_oharm_generic_csv\övrigt.csv""   # Source CSV (Comma Separated Value) File(s)
- FEATURE_TYPES = Anläggningar Anläggningar_2 Eldgivning Enhet Krypgångar Kulle Kulle_2 övrigt
- DestDataset_CSV2 = C:\Users\krima354\Work Folders\Documents\kicki_arbetsfiler\dap\utdata\lerharen\ohar_generic8   # Destination CSV (Comma Separated Value) Folder

Readers:
- CSV2_1: CSV2 from $(SourceDataset_CSV2)

Writers:
- CSV2_2: CSV2 to $(DestDataset_CSV2)

Anläggningar (reader CSV2_1)
    attributes: AnlÃƒÂ¤ggn varchar(10), UUID uint32, geom varchar(593), Eldgivning varchar(1), Enhet varchar(1), KrypgÃƒÂ¥n varchar(1), Kulle varchar(1), ÃƒÂ¶vrigt uint32
    -> AttributeManager
AttributeManager
    ATTR_TABLE = RENAME_SET_VALUE fme_basename > filnamn
    -> File1 (writer CSV2_2)
File1 (writer CSV2_2)
    attributes: AnlÃƒÂ¤ggn varchar(10), UUID uint32, geom varchar(593), Eldgivning varchar(1), Enhet varchar(1), KrypgÃƒÂ¥n varchar(1), Kulle varchar(1), ÃƒÂ¶vrigt uint32, filnamn varchar(50)
