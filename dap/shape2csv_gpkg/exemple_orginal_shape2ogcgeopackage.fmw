FME workspace exemple_orginal_shape2ogcgeopackage.fmw

Parameters:
- SourceDataset_GENERIC = ""C:\Users\krima354\Box\SweDigArch M3\Indata\DAP\Sakarias Arbetsmaterial\Omprojicerad och bearbetad data\Gävleborg 2\Länsmuseet Gävleborg_2004_01 Måndagsbäcken\A1.shp" "C:\Users\krima354\Box\SweDigArch M3\Indata\DAP\Sakarias Arbetsmaterial\Omprojicerad och bearbetad data\Gävleborg 2\Länsmuseet Gävleborg_2004_01 Måndagsbäcken\A1_2.shp" "C:\Users\krima354\Box\SweDigArch M3\Indata\DAP\Sakarias Arbetsmaterial\Omprojicerad och bearbetad data\Gävleborg 2\Länsmuseet Gävleborg_2004_01 Måndagsbäcken\A2.shp" "C:\Users\krima354\Box\SweDigArch M3\Indata\DAP\Sakarias Arbetsmaterial\Omprojicerad och bearbetad data\Gävleborg 2\Länsmuseet Gävleborg_2004_01 Måndagsbäcken\Höjder.shp" "C:\Users\krima354\Box\SweDigArch M3\Indata\DAP\Sakarias Arbetsmaterial\Omprojicerad och bearbetad data\Gävleborg 2\Länsmuseet Gävleborg_2004_01 Måndagsbäcken\Höjder_2.shp" "C:\Users\krima354\Box\SweDigArch M3\Indata\DAP\Sakarias Arbetsmaterial\Omprojicerad och bearbetad data\Gävleborg 2\Länsmuseet Gävleborg_2004_01 Måndagsbäcken\Schakt F.shp" "C:\Users\krima354\Box\SweDigArch M3\Indata\DAP\Sakarias Arbetsmaterial\Omprojicerad och bearbetad data\Gävleborg 2\Länsmuseet Gävleborg_2004_01 Måndagsbäcken\Schakt.shp" "C:\Users\krima354\Box\SweDigArch M3\Indata\DAP\Sakarias Arbetsmaterial\Omprojicerad och bearbetad data\Gävleborg 2\Länsmuseet Gävleborg_2004_01 Måndagsbäcken\Schakt_N.shp" "C:\Users\krima354\Box\SweDigArch M3\Indata\DAP\Sakarias Arbetsmaterial\Omprojicerad och bearbetad data\Gävleborg 2\Länsmuseet Gävleborg_2004_01 Måndagsbäcken\Sten_ytaB.shp" "C:\Users\krima354\Box\SweDigArch M3\Indata\DAP\Sakarias Arbetsmaterial\Omprojicerad och bearbetad data\Gävleborg 2\Länsmuseet Gävleborg_2004_01 Måndagsbäcken\Sten_ytaB_2.shp" "C:\Users\krima354\Box\SweDigArch M3\Indata\DAP\Sakarias Arbetsmaterial\Omprojicerad och bearbetad data\Gävleborg 2\Länsmuseet Gävleborg_2004_01 Måndagsbäcken\Sten_ytaB_3.shp" "C:\Users\krima354\Box\SweDigArch M3\Indata\DAP\Sakarias Arbetsmaterial\Omprojicerad och bearbetad data\Gävleborg 2\Länsmuseet Gävleborg_2004_01 Måndagsbäcken\Sten_ytaBD.shp" "C:\Users\krima354\Box\SweDigArch M3\Indata\DAP\Sakarias Arbetsmaterial\Omprojicerad och bearbetad data\Gävleborg 2\Länsmuseet Gävleborg_2004_01 Måndagsbäcken\Sten_ytaBD_2.shp" "C:\Users\krima354\Box\SweDigArch M3\Indata\DAP\Sakarias Arbetsmaterial\Omprojicerad och bearbetad data\Gävleborg 2\Länsmuseet Gävleborg_2004_01 Måndagsbäcken\Sten_ytaC.shp" "C:\Users\krima354\Box\SweDigArch M3\Indata\DAP\Sakarias Arbetsmaterial\Omprojicerad och bearbetad data\Gävleborg 2\Länsmuseet Gävleborg_2004_01 Måndagsbäcken\Sten_ytaC2.shp" "C:\Users\krima354\Box\SweDigArch M3\Indata\DAP\Sakarias Arbetsmaterial\Omprojicerad och bearbetad data\Gävleborg 2\Länsmuseet Gävleborg_2004_01 Måndagsbäcken\Sten_ytaD.shp" "C:\Users\krima354\Box\SweDigArch M3\Indata\DAP\Sakarias Arbetsmaterial\Omprojicerad och bearbetad data\Gävleborg 2\Länsmuseet Gävleborg_2004_01 Måndagsbäcken\Sten_ytaD_2.shp" "C:\Users\krima354\Box\SweDigArch M3\Indata\DAP\Sakarias Arbetsmaterial\Omprojicerad och bearbetad data\Gävleborg 2\Länsmuseet Gävleborg_2004_01 Måndagsbäcken\Sten_ytaE.shp" "C:\Users\krima354\Box\SweDigArch M3\Indata\DAP\Sakarias Arbetsmaterial\Omprojicerad och bearbetad data\Gävleborg 2\Länsmuseet Gävleborg_2004_01 Måndagsbäcken\Totalkvarts.shp" "C:\Users\krima354\Box\SweDigArch M3\Indata\DAP\Sakarias Arbetsmaterial\Omprojicerad och bearbetad data\Gävleborg 2\Länsmuseet Gävleborg_2004_01 Måndagsbäcken\totalkvartsit.shp""   # Source Dataset
- DestDataset_OGCGEOPACKAGE = $(FME_MF_DIR)mandagsbacken_kopia_av_shape.gpkg   # GeoPackage File

Readers:
- GENERIC_1: GENERIC from $(SourceDataset_GENERIC)

Writers:
- OGCGEOPACKAGE_1: OGCGEOPACKAGE to $(DestDataset_OGCGEOPACKAGE)

A1 (reader GENERIC_1)
    attributes: mÃƒÂ¥a1 varchar(10), UUID varchar(51)
    -> A1 (writer OGCGEOPACKAGE_1)
A1 (writer OGCGEOPACKAGE_1)
    attributes: mÃƒÂ¥a1 text(10), UUID text(51)
A1_2 (reader GENERIC_1)
    attributes: mÃƒÂ¥a1 varchar(10), UUID varchar(51)
    -> A1_2 (writer OGCGEOPACKAGE_1)
A1_2 (writer OGCGEOPACKAGE_1)
    attributes: mÃƒÂ¥a1 text(10), UUID text(51)
A2 (reader GENERIC_1)
    attributes: mÃƒÂ¥a2 varchar(10), UUID varchar(51)
    -> A2 (writer OGCGEOPACKAGE_1)
A2 (writer OGCGEOPACKAGE_1)
    attributes: mÃƒÂ¥a2 text(10), UUID text(51)
Höjder (reader GENERIC_1)
    attributes: mÃƒÂ¥h2 varchar(10), UUID varchar(51)
    -> Höjder (writer OGCGEOPACKAGE_1)
Höjder (writer OGCGEOPACKAGE_1)
    attributes: mÃƒÂ¥h2 text(10), UUID text(51)
Höjder_2 (reader GENERIC_1)
    attributes: mÃƒÂ¥h2 varchar(10), UUID varchar(51)
    -> Höjder_2 (writer OGCGEOPACKAGE_1)
Höjder_2 (writer OGCGEOPACKAGE_1)
    attributes: mÃƒÂ¥h2 text(10), UUID text(51)
Schakt (reader GENERIC_1)
    attributes: mÃƒÂ¥h varchar(10), UUID varchar(51)
    -> Schakt (writer OGCGEOPACKAGE_1)
Schakt (writer OGCGEOPACKAGE_1)
    attributes: mÃƒÂ¥h text(10), UUID text(51)
Schakt F (reader GENERIC_1)
    attributes: mÃƒÂ¥f1 varchar(10), UUID varchar(51)
    -> Schakt F (writer OGCGEOPACKAGE_1)
Schakt F (writer OGCGEOPACKAGE_1)
    attributes: mÃƒÂ¥f1 text(10), UUID text(51)
Schakt_N (reader GENERIC_1)
    attributes: mÃƒÂ¥h varchar(10), UUID varchar(51)
    -> Schakt_N (writer OGCGEOPACKAGE_1)
Schakt_N (writer OGCGEOPACKAGE_1)
    attributes: mÃƒÂ¥h text(10), UUID text(51)
Sten_ytaB (reader GENERIC_1)
    attributes: mÃƒÂ¥b1 varchar(10), UUID varchar(51)
    -> Sten_ytaB (writer OGCGEOPACKAGE_1)
Sten_ytaB (writer OGCGEOPACKAGE_1)
    attributes: mÃƒÂ¥b1 text(10), UUID text(51)
Sten_ytaB_2 (reader GENERIC_1)
    attributes: mÃƒÂ¥b1 varchar(10), UUID varchar(51)
    -> Sten_ytaB_2 (writer OGCGEOPACKAGE_1)
Sten_ytaB_2 (writer OGCGEOPACKAGE_1)
    attributes: mÃƒÂ¥b1 text(10), UUID text(51)
Sten_ytaB_3 (reader GENERIC_1)
    attributes: mÃƒÂ¥b1 varchar(10), UUID varchar(51)
    -> Sten_ytaB_3 (writer OGCGEOPACKAGE_1)
Sten_ytaB_3 (writer OGCGEOPACKAGE_1)
    attributes: mÃƒÂ¥b1 text(10), UUID text(51)
Sten_ytaBD (reader GENERIC_1)
    attributes: mÃƒÂ¥bd varchar(10), UUID varchar(51)
    -> Sten_ytaBD (writer OGCGEOPACKAGE_1)
Sten_ytaBD (writer OGCGEOPACKAGE_1)
    attributes: mÃƒÂ¥bd text(10), UUID text(51)
Sten_ytaBD_2 (reader GENERIC_1)
    attributes: mÃƒÂ¥bd varchar(10), UUID varchar(51)
    -> Sten_ytaBD_2 (writer OGCGEOPACKAGE_1)
Sten_ytaBD_2 (writer OGCGEOPACKAGE_1)
    attributes: mÃƒÂ¥bd text(10), UUID text(51)
Sten_ytaC (reader GENERIC_1)
    attributes: mÃƒÂ¥c1 varchar(10), UUID varchar(51)
    -> Sten_ytaC (writer OGCGEOPACKAGE_1)
Sten_ytaC (writer OGCGEOPACKAGE_1)
    attributes: mÃƒÂ¥c1 text(10), UUID text(51)
Sten_ytaC2 (reader GENERIC_1)
    attributes: mÃƒÂ¥c1x varchar(10), UUID varchar(51)
    -> Sten_ytaC2 (writer OGCGEOPACKAGE_1)
Sten_ytaC2 (writer OGCGEOPACKAGE_1)
    attributes: mÃƒÂ¥c1x text(10), UUID text(51)
Sten_ytaD (reader GENERIC_1)
    attributes: mÃƒÂ¥d1 varchar(10), UUID varchar(51)
    -> Sten_ytaD (writer OGCGEOPACKAGE_1)
Sten_ytaD (writer OGCGEOPACKAGE_1)
    attributes: mÃƒÂ¥d1 text(10), UUID text(51)
Sten_ytaD_2 (reader GENERIC_1)
    attributes: mÃƒÂ¥d1 varchar(10), UUID varchar(51)
    -> Sten_ytaD_2 (writer OGCGEOPACKAGE_1)
Sten_ytaD_2 (writer OGCGEOPACKAGE_1)
    attributes: mÃƒÂ¥d1 text(10), UUID text(51)
Sten_ytaE (reader GENERIC_1)
    attributes: mÃƒÂ¥e1 varchar(10), UUID varchar(51)
    -> Sten_ytaE (writer OGCGEOPACKAGE_1)
Sten_ytaE (writer OGCGEOPACKAGE_1)
    attributes: mÃƒÂ¥e1 text(10), UUID text(51)
Totalkvarts (reader GENERIC_1)
    attributes: N1 real64, N2 int32, N3 real64, N4 real64, N5 real64, N6 real64, N7 real64, UUID varchar(51)
    -> Totalkvarts (writer OGCGEOPACKAGE_1)
Totalkvarts (writer OGCGEOPACKAGE_1)
    attributes: N1 double, N2 mediumint, N3 double, N4 double, N5 double, N6 double, N7 double, UUID text(51)
totalkvartsit (reader GENERIC_1)
    attributes: N1 real64, N2 real64, N3 real64, N4 real32, N5 real64, N6 real64, N7 real32, UUID varchar(51)
    -> totalkvartsit (writer OGCGEOPACKAGE_1)
totalkvartsit (writer OGCGEOPACKAGE_1)
    attributes: N1 double, N2 double, N3 double, N4 float, N5 double, N6 double, N7 float, UUID text(51)
