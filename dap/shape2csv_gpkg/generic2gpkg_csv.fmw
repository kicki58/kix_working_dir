FME workspace generic2gpkg_csv.fmw

Parameters:
- SourceDataset_GENERIC = ""C:\Users\krima354\Box\SweDigArch M3\Indata\DAP\Sakarias Arbetsmaterial\Omprojicerad och bearbetad data\Gävleborg 2\Länsmuseet Gävleborg_2014_22 Avrättningsplats_i_Rengsjö\fynd.shp" "C:\Users\krima354\Box\SweDigArch M3\Indata\DAP\Sakarias Arbetsmaterial\Omprojicerad och bearbetad data\Gävleborg 2\Länsmuseet Gävleborg_2014_22 Avrättningsplats_i_Rengsjö\fynd__vrigt.shp" "C:\Users\krima354\Box\SweDigArch M3\Indata\DAP\Sakarias Arbetsmaterial\Omprojicerad och bearbetad data\Gävleborg 2\Länsmuseet Gävleborg_2014_22 Avrättningsplats_i_Rengsjö\fynd__vrigt_2.shp" "C:\Users\krima354\Box\SweDigArch M3\Indata\DAP\Sakarias Arbetsmaterial\Omprojicerad och bearbetad data\Gävleborg 2\Länsmuseet Gävleborg_2014_22 Avrättningsplats_i_Rengsjö\grav.shp" "C:\Users\krima354\Box\SweDigArch M3\Indata\DAP\Sakarias Arbetsmaterial\Omprojicerad och bearbetad data\Gävleborg 2\Länsmuseet Gävleborg_2014_22 Avrättningsplats_i_Rengsjö\Nedgrävning.shp" "C:\Users\krima354\Box\SweDigArch M3\Indata\DAP\Sakarias Arbetsmaterial\Omprojicerad och bearbetad data\Gävleborg 2\Länsmuseet Gävleborg_2014_22 Avrättningsplats_i_Rengsjö\profil.shp" "C:\Users\krima354\Box\SweDigArch M3\Indata\DAP\Sakarias Arbetsmaterial\Omprojicerad och bearbetad data\Gävleborg 2\Länsmuseet Gävleborg_2014_22 Avrättningsplats_i_Rengsjö\sko.shp" "C:\Users\krima354\Box\SweDigArch M3\Indata\DAP\Sakarias Arbetsmaterial\Omprojicerad och bearbetad data\Gävleborg 2\Länsmuseet Gävleborg_2014_22 Avrättningsplats_i_Rengsjö\sten.shp" "C:\Users\krima354\Box\SweDigArch M3\Indata\DAP\Sakarias Arbetsmaterial\Omprojicerad och bearbetad data\Gävleborg 2\Länsmuseet Gävleborg_2014_22 Avrättningsplats_i_Rengsjö\stenröse.shp" "C:\Users\krima354\Box\SweDigArch M3\Indata\DAP\Sakarias Arbetsmaterial\Omprojicerad och bearbetad data\Gävleborg 2\Länsmuseet Gävleborg_2014_22 Avrättningsplats_i_Rengsjö\Undersökningsområde.shp""   # Source Dataset
- sokvag = C:\Users\krima354\Box\SweDigArch M3\Indata\DAP\Kickis_arbetsmaterial\utdata   # Välj mapp
- filnamn = avrattning
- COORDSYS = EPSG:3006   # COORDSYS Coordinate System indata

Readers:
- GENERIC_1: GENERIC from $(SourceDataset_GENERIC) in $(COORDSYS)

Writers:
- OGCGEOPACKAGE_1: OGCGEOPACKAGE to $(sokvag)/$(filnamn)/$(filnamn).gpkg in EPSG:3006
- CSV2_2: CSV2 to $(sokvag)\$(filnamn)\$(filnamn)_cvs.zip in EPSG:3006

NewFeatureType (reader GENERIC_1)
    -> Table1 (writer OGCGEOPACKAGE_1)
    -> GeometryExtractor
Table1 (writer OGCGEOPACKAGE_1)
GeometryExtractor
    ATTR = geom
    KIND_LONG = OGC Well Known Text
    OGCVERSION = 1.2
    OGC_WKT_PRECISION_DISPLAY = 64-bit
    REMOVE_GEOMETRY = No
    -> File1 (writer CSV2_2)
File1 (writer CSV2_2)
    attributes: geom string
